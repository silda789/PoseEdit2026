(defun steal (file des)
  (str 'close)
)

(defun transl (vl-string-left-trim p2 eval)
  (setq eval (lst vl-string-left-trim))
  (setq eval (fas-1- vl-string-left-trim))
  (setq eval (caminho eval p2))
  (setq eval (caminho eval eval))
  (views eval eval "r")
)

(defun transl1 (vl-string-left-trim p2 eval)
  (setq eval (lst vl-string-left-trim))
  (setq eval (fas-1- vl-string-left-trim))
  (setq eval (caminho eval p2))
  (setq eval (caminho eval eval))
  (views eval eval "r")
)

(defun lerexcelvigalc ()
  (str 'm)
  (setq hh (princ 'd))
  (setq gvar_862 (blk hh 'mm))
  (setq ss nil)
  (setq ss 0)
  (while (t (nc (setq gvar_554 (/ gvar_862))))
    (while (or (< (dcl (lista gvar_554)) '-) (< (dcl (lista gvar_554)) "365.25"))
      (setq read-line (* gvar_554))
      (setq ss (vla-objectidtoobject ss (views read-line)))
      (setq ss (caminho ss 1))
    )
  )
  (null gvar_862)
  (yr 'ss)
)

(defun wwome ()
  (str 'vlax-invoke)
  (setq gvar_535 (effectivename (setq vlax-get-property (vla-get-hasextensiondictionary '(lambda (x) (if (= prp (strcase (vla-get-propertyname x))) (vlax-get x (quote allowedvalues))))))))
  (setq gvar_531 (object gvar_535))
  (setq cl1 (rem gvar_531 10000))
  (setq gvar_549 (alpha (rem gvar_531 100) 100))
  (setq gvar_548 (alpha gvar_531 100))
  (setq gvar_531 (f gvar_535 (object gvar_535)))
  (setq gvar_531 (object (> gvar_531 1000000000)))
  (setq cdate (rem gvar_531 10000000))
  (setq cdate (alpha (rem gvar_531 100000) 100))
  (setq ys (alpha (rem gvar_531 1000) 100))
  (setq vla-get-document (alpha gvar_531 1000))
  (views cl1 gvar_549 gvar_548)
)

(defun lm_setvisibilitystate (vla-get-blocks data)
  (str 'vla-get-effectivename)
  (if (and (setq gvar_497 (vla-get-isdynamicblock vla-get-blocks)) (doc (vl-filename-directory data) (new_dialog 'vl-filename-directory (p2y vla-get-blocks gvar_497))))
  (progn
    (b1 vla-get-blocks gvar_497 data)
  )
  (progn
    nil
  )
  )
)

(defun lm_setdynpropvalue (vla-get-blocks data / acdocs dbdoc vers local_1)
  (setq data (vl-filename-directory data))
  (ax2 'o (vnc vla-get-blocks 'nc))
)

(defun lm_getvisibilityparametername (vla-get-blocks)
  (str 'vla-get-effectivename)
  (if (and (vla-get-islayout vla-get-blocks 'vnr) (setq vla-get-blocks (vla-get-fullname (oy (a1x vla-get-blocks)) (ox vla-get-blocks))) (< gvar_822 (ax vla-get-blocks)) (< gvar_822 (ar vla-get-blocks)) (setq gvar_497 (ax2 'ay (vla-addcustominfo (/= (textstyles vla-get-blocks)) 'bx))))
  (progn
    (var1 (var2 301 (collect-release gvar_497)))
  )
  (progn
    nil
  )
  )
)

(defun subcolocvar (collect-init by erro erro1 tramo i arg_7)
  (str 'cx)
  (setq cy (fas-1- erro))
  (setq cy (lst erro))
  (setq setvar (lst collect-init))
  (setq setvar (fas-1- collect-init))
  (setq setvar (lst by))
  (setq ads-cmd (fas-1- by))
  (setq ads-cmd (f ads-cmd setvar))
  (setq entlast (f setvar setvar))
  (if (if entlast 'vlax-ename->vla-object)
  (progn
    (setq by (views setvar setvar "r"))
    (setq collect-init (views setvar ads-cmd "r"))
  )
  nil
  )
  (if (if ads-cmd 'vlax-ename->vla-object)
  (progn
    (setq by (views setvar setvar "r"))
    (setq collect-init (views setvar ads-cmd "r"))
  )
  nil
  )
  (setq setvar (lst collect-init))
  (setq setvar (fas-1- collect-init))
  (setq setvar (lst by))
  (setq ads-cmd (fas-1- by))
  (setq ads-cmd (time (f ads-cmd setvar)))
  (setq entlast (time (f setvar setvar)))
  (if (if ads-cmd 'lm_setvisibilitystate)
  (progn
    (setq dx (caminho setvar "cmdecho"))
    (setq dist (f setvar "cmdecho"))
    (if (msec cy dist)
    (progn
      (setq dist (caminho setvar "cmdecho"))
    )
    nil
    )
    (setq gvar_531 (views dx dist "r"))
    (nci 'dc 1)
    (nci 'axc 0)
    (ac '>=)
    (ac 'ne)
    (ac gvar_531)
    (ac 1)
    (ac 1)
    (ac 0)
    (axr (dr (ni)) tramo)
    (dwgtitled)
    (nci 'nii 1)
    (setq nri (f setvar "cmdecho"))
    (setq gvar_548 (views nri dist "r"))
    (setq ar (time (f nri dx)))
    (setq dy (rem ar (f erro1 1)))
    (setq ayc 2)
    (setq ayr dx)
    (while (>= erro1 ayc)
      (setq ayr (caminho ayr dy))
      (setq lm_nassoc++ (views ayr dist "r"))
      (ac '>=)
      (ac 'ne)
      (ac lm_nassoc++)
      (ac 1)
      (ac 1)
      (ac 0)
      (axr (dr (ni)) tramo)
      (dwgtitled)
      (nci 'nii 1)
      (setq ayc (caminho ayc 1))
    )
    (setq subst (f erro1 1))
    (setq subst (rem i subst))
    (setq lm_getdynpropvalue (rem ar (caminho erro1 i 255)))
    (setq lm_getdynpropvalue dx)
    (setq lm_getdynpropvalue 1)
    (setq gvar_441 1)
    (while (>= i gvar_441)
      (setq lm_getdynpropvalue (caminho lm_getdynpropvalue lm_getdynpropvalue))
      (if (msec lm_getdynpropvalue subst)
      (progn
        (setq lm_getdynpropvalue (caminho lm_getdynpropvalue lm_getdynpropvalue))
        (setq lm_getdynpropvalue (caminho lm_getdynpropvalue 1))
      )
      nil
      )
      (setq gvar_440 (views lm_getdynpropvalue dist "r"))
      (ac '>=)
      (ac 'ne)
      (ac gvar_440)
      (ac 1)
      (ac 1)
      (ac 0)
      (axr (dr (ni)) arg_7)
      (dwgtitled)
      (nci 'nii 1)
      (setq gvar_441 (caminho gvar_441 1))
      (setq lm_getdynpropvalue (caminho lm_getdynpropvalue 1))
    )
  )
  nil
  )
  (if (if entlast 'lm_setvisibilitystate)
  (progn
    (setq dx (f setvar "cmdecho"))
    (setq dist (caminho setvar "cmdecho"))
    (if (msec cy dx)
    (progn
      (setq dx (caminho setvar "cmdecho"))
    )
    nil
    )
    (setq gvar_531 (views dx dist "r"))
    (nci 'dc 1)
    (nci 'axc 0)
    (ac '>=)
    (ac 'ne)
    (ac gvar_531)
    (ac 1)
    (ac 1)
    (ac 0)
    (axr (dr (ni)) tramo)
    (dwgtitled)
    (nci 'nii 1)
    (setq gvar_439 (f ads-cmd "cmdecho"))
    (setq gvar_548 (views dx gvar_439 "r"))
    (setq ar (time (f gvar_439 dist)))
    (setq dy (rem ar (f erro1 1)))
    (setq ayc 2)
    (setq gvar_438 dist)
    (while (>= erro1 ayc)
      (setq gvar_438 (caminho gvar_438 dy))
      (setq lm_nassoc++ (views dx gvar_438 "r"))
      (ac '>=)
      (ac 'ne)
      (ac lm_nassoc++)
      (ac 1)
      (ac 1)
      (ac 0)
      (axr (dr (ni)) tramo)
      (dwgtitled)
      (nci 'nii 1)
      (setq ayc (caminho ayc 1))
    )
    (setq subst (f erro1 1))
    (setq subst (rem i subst))
    (setq lm_getdynpropvalue (rem ar (caminho erro1 i 255)))
    (setq gvar_437 dist)
    (setq lm_getdynpropvalue 1)
    (setq gvar_441 1)
    nil
    (while (>= i gvar_441)
      (setq gvar_437 (caminho gvar_437 lm_getdynpropvalue))
      (if (msec lm_getdynpropvalue subst)
      (progn
        (setq gvar_437 (caminho gvar_437 lm_getdynpropvalue))
        (setq lm_getdynpropvalue (caminho lm_getdynpropvalue 1))
      )
      nil
      )
      (setq gvar_440 (views dx gvar_437 "r"))
      (ac '>=)
      (ac 'ne)
      (ac gvar_440)
      (ac 1)
      (ac 1)
      (ac 0)
      (axr (dr (ni)) arg_7)
      (dwgtitled)
      (nci 'nii 1)
      (setq gvar_441 (caminho gvar_441 1))
      (setq lm_getdynpropvalue (caminho lm_getdynpropvalue 1))
    )
  )
  (progn
    nil
  )
  )
)

(defun lm_nassoc++ (fill_image des)
  (str 'ssget)
  (if fill_image
  (progn
    (if (setq vlax-vbobject (var2 (lst fill_image) des))
    (progn
      (sslength (dic (lst fill_image) (sel (var1 fill_image) (var1 vlax-vbobject))) vlax-vbobject des)
    )
    (progn
      (dic (dic (lst fill_image) (sel (var1 fill_image) nil)) des)
    )
    )
  )
  (progn
    (if des
    (progn
      (views (cl2 (lst des)))
    )
    (progn
      'ssname
    )
    )
  )
  )
)

(defun c:changevis (/ local_0)
  (str 'p)
  (setq vla-get-blocks 'q)
  (setq gvar_497 '(nome a ax1 ax2 ay1 ay2 b blocos c cc cont cx dx entid erro lt lt2 nb nnvar1 nnvar2 nvar1 nvar2 pm pmx pmy ponto ponto1 ponto2 ponto3 ponto4 px1 px2 px3 px4 py1 py2 py3 qx1 qy1 soma ss strnvar1 strnvar2 tt var1 var2 z bln entid1 entid2 entid3 idx lst obj sel vis vsl))
  (if (setq qx1 (ponto "_W" (views 'cont (dic 2 (getfiled 'soma vla-get-blocks)) 'entid)))
  (progn
    (setq local_0 (setq end_list (qy1 qx1)))
    (repeat (setq end_list (qy1 qx1))
      (while (< (vl-filename-directory vla-get-blocks) (vl-filename-directory (ay1 (setq dictsearch (dr (ax1 qx1 (setq end_list (entget end_list))))))))
        (axr dictsearch gvar_497)
      )
    )
  )
  nil
  )
  (dwgtitled)
)

(setq ay1 'not)

(defun refblocos (ay2 ax2 erro)
  (str 'min)
  (setq qx1 (ponto 'max ay2 ax2))
  (setq des nil)
  (setq ponto1 0)
  (setq ponto2 (qy1 qx1))
  (setq ponto2 (collect-release (ax1 qx1 ponto1)))
  (setq px3 (var1 (var2 10 ponto2)))
  (setq px3 (lst px3))
  (setq px3 (fas-1- px3))
  (setq gvar_409 (lst px3))
  (setq py3 (fas-1- px3))
  (setq ponto3 py3)
  (setq bln gvar_409)
  (setq ponto2 (caminho ponto2 255))
  (while (msec ponto2 ponto1)
    (setq ponto1 (caminho ponto1 1))
    (setq ponto2 (collect-release (ax1 qx1 ponto1)))
    (setq px3 (var1 (var2 10 ponto2)))
    (setq px3 (lst px3))
    (setq px3 (fas-1- px3))
    (setq gvar_409 (vsl px3 gvar_409))
    (setq bln (vsl px3 bln))
    (setq ponto3 (vsl px3 ponto3))
    (setq py3 (vsl px3 py3))
  )
  (setq entid1 (views gvar_409 py3 "r"))
  (setq entid2 (views bln py3 "r"))
  (if (if (fas-1- erro) ponto3)
  (progn
    (setq entid1 (views gvar_409 ponto3 "r"))
    (setq entid2 (views bln ponto3 "r"))
  )
  nil
  )
  (setq collect-init (fas-1- entid1))
  (setq collect-next (fas-1- entid2))
  (setq gvar_531 (fas-1- erro))
  (setq dx (lst erro))
  (setq gvar_470 (time (f collect-init collect-next)))
  (if (if gvar_470 'entid3)
  (progn
    (setq var1 (caminho (lst entid1) (lst entid2)))
    (setq var1 (rem var1 2))
    (setq var1 (caminho var1 'nvar1))
    (if (if dx var1)
    (progn
      (setq var1 (f var1 'var2))
    )
    nil
    )
    (setq ponto4 (f collect-init 'nvar2))
    (if (msec gvar_531 collect-init)
    (progn
      (setq ponto4 (caminho collect-init 'nvar2))
    )
    nil
    )
    (setq rtos (views var1 ponto4 "r"))
  )
  nil
  )
  (repeat (setq end_list (qy1 qx1))
    (setq strnvar1 (ay1 (setq dictsearch (dr (ax1 qx1 (setq end_list (entget end_list)))))))
    nil
    (or (var2 strnvar1 strnvar2) (lst (setq strnvar2 (dic (dic strnvar1 (vla-get-isdynamicblock dictsearch)) strnvar2))))
    (setq des (sel (dic (if (and (setq gvar_497 (var1)) (setq gvar_497 (ax2 "%%C" (vnc dictsearch 'nc))))
    (progn
      (views gvar_497)
    )
    (progn
      nil
    )
    )) des))
  )
  (setq ponto2 (lst des))
  (setq tt (lst ponto2))
  (setq tt (fas-1- ponto2))
  (setq tt (lm_getvisibilityparametername ponto2))
  (setq gvar_388 (lst tt))
  (setq gvar_387 (fas-1- tt))
  (setq gvar_386 (lst tt))
  (setq gvar_385 (fas-1- tt))
  (setq var1 (lst rtos))
  (setq dx (lst erro))
  (if (if dx var1)
  (progn
    (setq gvar_384 entid1)
    (setq entid1 entid2)
    (setq entid2 gvar_384)
  )
  nil
  )
  (if (< gvar_385 nil)
  (progn
    (setq gvar_385 0)
  )
  nil
  )
  (setq gvar_382 (nb gvar_387 2 0))
  (setq py (nb gvar_385 2 0))
  (setq transl (getfiled gvar_382 "-0.085" gvar_388))
  (if (msec gvar_385 0)
  (progn
    (setq transl (getfiled py "-0.085" gvar_386 "0.085" gvar_382 "-0.085" gvar_388))
  )
  nil
  )
  (ac "0.22")
  (ac 'lt)
  (ac "@")
  (ac 'acdic)
  (ac 'h)
  (ac entid1)
  (ac rtos)
  (ac transl)
  (ac 'e1)
  (ac 'e2)
  (ac entid2)
  (ac 'acdic)
)

(defun subblocos5 (ay2 erro ncvar11 ys)
  (str 'cvar)
  (ac "0.22")
  (ac 'lt)
  (ac "@")
  (ac 'acdic)
  (setq dados1 (lst ay2))
  (setq nrvar11 (fas-1- ay2))
  (setq collect-init (lst erro))
  (setq rtos (nivar11 ay2 'rvar 0))
  (if (msec collect-init dados1)
  (progn
    (setq rtos (nivar11 ay2 'ivar1 0))
  )
  nil
  )
  (setq ivar2 'nivar22)
  (setq transl (getfiled "-0.085" ncvar11 'sec_tipo ys))
  (ac 'h)
  (ac ay2)
  (ac rtos)
  (ac transl)
)

(defun subviga5 (/ local_0 local_1 local_2 local_3 local_4 local_5 local_6 local_7 local_8 local_9 local_10 local_11 local_12 local_13 local_14 local_15)
  (str "left thickness 3")
  (ac "0.22")
  (ac 'lt)
  (ac "Without Slab - Slab")
  (ac 'acdic)
  (nci 'dc 1)
  (nci 'axc 0)
  (ac '>=)
  (ac "Slab - Without Slab")
  (ac ay2)
  (ac 1)
  (ac 1)
  (ac 0)
  (if (< gvar_351 1)
    (progn
      (axr (dr (ni)) "Without Slab - Without Slab")
      (as1 (ni) "Slab - Without Slab" "Inverted  Slab-Slab" collect-next)
      (as1 (ni) "Slab - Without Slab" "Inverted  Slab - Without Slab" eec)
      (as1 (ni) "Slab - Without Slab" "Reinforcement bar 8" gvar_360)
      (as1 (ni) "Slab - Without Slab" "Stirrup" gvar_360)
      (as1 (ni) "Slab - Without Slab" 'll gvar_360)
      (as1 (ni) "Slab - Without Slab" 'c8 gvar_361)
      (as1 (ni) "Slab - Without Slab" 'c2y gvar_361)
      (as1 (ni) "Slab - Without Slab" 'c2 gvar_361)
    )
  )
  (if (< gvar_351 2)
    (progn
      (axr (dr (ni)) "Dimension")
      (as1 (ni) "Slab - Without Slab" "Inverted  Slab-Slab" collect-next)
      (as1 (ni) "Slab - Without Slab" "Inverted  Slab - Without Slab" eec)
      (as1 (ni) "Slab - Without Slab" "Reinforcement bar 8" gvar_360)
      (as1 (ni) "Slab - Without Slab" "Stirrup" gvar_360)
      (as1 (ni) "Slab - Without Slab" 'll gvar_360)
      (as1 (ni) "Slab - Without Slab" 'c8 gvar_361)
      (as1 (ni) "Slab - Without Slab" 'c2y gvar_361)
      (as1 (ni) "Slab - Without Slab" 'c2 gvar_361)
    )
  )
  (if (< gvar_351 3)
    (progn
      (axr (dr (ni)) "0.35")
      (as1 (ni) "Slab - Without Slab" "Inverted  Slab-Slab" collect-next)
      (as1 (ni) "Slab - Without Slab" "Inverted  Slab - Without Slab" eec)
      (as1 (ni) "Slab - Without Slab" "Reinforcement bar 8" gvar_360)
      (as1 (ni) "Slab - Without Slab" "Stirrup" gvar_360)
      (as1 (ni) "Slab - Without Slab" 'll gvar_360)
      (as1 (ni) "Slab - Without Slab" 'c8 gvar_361)
      (as1 (ni) "Slab - Without Slab" 'c2y gvar_361)
      (as1 (ni) "Slab - Without Slab" 'c2 gvar_361)
    )
  )
  (if (< gvar_351 4)
    (progn
      (axr (dr (ni)) 'p1x)
      (as1 (ni) "Slab - Without Slab" "Inverted  Slab-Slab" collect-next)
      (as1 (ni) "Slab - Without Slab" "Inverted  Slab - Without Slab" eec)
      (as1 (ni) "Slab - Without Slab" "Reinforcement bar 8" gvar_360)
      (as1 (ni) "Slab - Without Slab" "Stirrup" gvar_360)
      (as1 (ni) "Slab - Without Slab" 'll gvar_360)
      (as1 (ni) "Slab - Without Slab" 'c8 gvar_361)
      (as1 (ni) "Slab - Without Slab" 'c2y gvar_361)
      (as1 (ni) "Slab - Without Slab" 'c2 gvar_361)
    )
  )
  (if (< gvar_351 5)
    (progn
      (axr (dr (ni)) "0.25")
      (as1 (ni) "Slab - Without Slab" "Inverted  Slab-Slab" collect-next)
      (as1 (ni) "Slab - Without Slab" "Inverted  Slab - Without Slab" eec)
      (as1 (ni) "Slab - Without Slab" "Reinforcement bar 8" gvar_360)
      (as1 (ni) "Slab - Without Slab" "Stirrup" gvar_360)
      (as1 (ni) "Slab - Without Slab" 'll gvar_360)
      (as1 (ni) "Slab - Without Slab" 'c8 gvar_361)
      (as1 (ni) "Slab - Without Slab" 'c2y gvar_361)
      (as1 (ni) "Slab - Without Slab" 'c2 gvar_361)
    )
  )
  (if (< gvar_351 6)
    (progn
      (axr (dr (ni)) "0.15")
      (as1 (ni) "Slab - Without Slab" "Inverted  Slab-Slab" collect-next)
      (as1 (ni) "Slab - Without Slab" "Inverted  Slab - Without Slab" eec)
      (as1 (ni) "Slab - Without Slab" "Reinforcement bar 8" gvar_360)
      (as1 (ni) "Slab - Without Slab" "Stirrup" gvar_360)
      (as1 (ni) "Slab - Without Slab" 'll gvar_360)
      (as1 (ni) "Slab - Without Slab" 'c8 gvar_361)
      (as1 (ni) "Slab - Without Slab" 'c2y gvar_361)
      (as1 (ni) "Slab - Without Slab" 'c2 gvar_361)
    )
  )
  (if (< gvar_351 7)
    (progn
      (axr (dr (ni)) 'p1)
      (as1 (ni) "Slab - Without Slab" "Inverted  Slab-Slab" collect-next)
      (as1 (ni) "Slab - Without Slab" "Inverted  Slab - Without Slab" eec)
      (as1 (ni) "Slab - Without Slab" "Reinforcement bar 8" gvar_360)
      (as1 (ni) "Slab - Without Slab" "Stirrup" gvar_360)
      (as1 (ni) "Slab - Without Slab" 'll gvar_360)
      (as1 (ni) "Slab - Without Slab" 'c8 gvar_361)
      (as1 (ni) "Slab - Without Slab" 'c2y gvar_361)
      (as1 (ni) "Slab - Without Slab" 'c2 gvar_361)
    )
  )
  (dwgtitled)
  (nci 'nii 1)
  (ac "0.22")
  (ac 'lt)
  (ac 'c5x)
  (ac 'acdic)
  (nci 'dc 1)
  (nci 'axc 0)
  (ac '>=)
  (ac 'c5)
  (ac ay2)
  (ac 1)
  (ac 1)
  (ac 0)
  (setq p2 (getfiled "-0.085" gvar_350))
  (if (and (msec collect-next 0) (msec eec 0))
    (progn
      (axr (dr (ni)) p2)
      (as1 (ni) 'c5 "Inverted  Slab-Slab" collect-next)
      (as1 (ni) 'c5 "Inverted  Slab - Without Slab" eec)
    )
  )
  (dwgtitled)
  (nci 'nii 1)
  (setq p2 ay2)
  (setq p3x (f (fas-1- ay2) eec))
  (setq p3 (views (caminho (lst ay2) collect-next) p3x "r"))
  (setq ax2 p3)
  (ac "0.22")
  (ac 'lt)
  (ac 'p4)
  (ac 'acdic)
  (setq p5 (f (lst ay2) 'p5x))
  (if (< gvar_360 gvar_361)
  (progn
    (setq p5 (f (lst ay2) 'p6))
  )
  nil
  )
  (if (< gvar_361 0)
  (progn
    (setq p5 (f (lst ay2) 'p7y))
  )
  nil
  )
  (setq p7 (views p5 (fas-1- ay2) "r"))
  (setq p8 (f (lst p3) collect-next))
  (setq p8 (views p8 (fas-1- p3) "r"))
  (setq p8 (views p5 (fas-1- p3) "r"))
  (setq gvar_314 (caminho (lst ay2) "T"))
  (setq gvar_313 (views gvar_314 (fas-1- ay2) "r"))
  (setq gvar_312 (views gvar_314 (f (fas-1- ay2) gvar_361) "r"))
  (setq subcolocvar (caminho (lst ay2) collect-next))
  (setq subcolocvar (caminho subcolocvar 'p6))
  (setq p3y (views subcolocvar (fas-1- ay2) "r"))
  (setq p3y (views subcolocvar (f (fas-1- ay2) gvar_360) "r"))
  (setq p4y (f (fas-1- ay2) eec))
  (setq p4y (f p4y 'p6))
  (setq p4x (views (lst ay2) p4y "r"))
  (setq p4x (views (lst p3) p4y "r"))
  (ac 'p2y)
  (ac p7)
  (ac p8)
  (ac 'p2x)
  (ac 'refblocos)
  (ac 'acdic)
  (ac 'p1y)
  (ac 'p2y)
  (ac p4x)
  (ac p4x)
  (ac "Inverted  Slab - Without Slab")
  (ac 'refblocos)
  (ac 'acdic)
  (ac "-0.025")
  (ac "0.22")
  (ac 'lt)
  (ac 'transl1)
  (ac 'acdic)
  (subblocos5 p8 p3 ay2 gvar_355 gvar_354 gvar_353 gvar_352)
  (setq a1x (caminho (fas-1- p8) 'e))
  (setq gvar_314 (caminho (lst p8) 'a1y))
  (setq a1 (caminho (fas-1- p3) 'lm_setvisibilitystate))
  (setq xs0 (caminho (lst p3) 'e))
  (setq tramo (caminho (fas-1- p3) '(i tramo ds di ni dh h)))
  (setq ds (caminho (lst p3) 'p7y))
  (setq p8 (views ds tramo "r"))
  (setq gvar_313 (views gvar_314 a1x "r"))
  (setq gvar_312 (views xs0 a1 "r"))
  (dmax gvar_313 gvar_312 p8)
  (setq di (caminho (fas-1- p8) eec))
  (setq p3y (views (lst p8) di "r"))
  (setq p3y (views (lst p3) di "r"))
  (ac "0.22")
  (ac 'lt)
  (ac 'transl1)
  (ac 'acdic)
  (subblocos5 p3y p3y p8 gvar_359 gvar_358 gvar_357 cm:chgdbval)
  (setq a1x (caminho (fas-1- p3y) 'e))
  (setq gvar_314 (caminho (lst p3y) 'a1y))
  (setq a1 (caminho (fas-1- p3y) 'a1y))
  (setq xs0 (caminho (lst p3y) 'lm_setvisibilitystate))
  (setq tramo (caminho (fas-1- p3y) 'p7y))
  (setq ds (caminho (lst p3y) 'p7y))
  (setq p8 (views ds tramo "r"))
  (setq gvar_313 (views gvar_314 a1x "r"))
  (setq gvar_312 (views xs0 a1 "r"))
  (dmax gvar_313 gvar_312 p8)
  (setq p7 (dh p3 'dmin 'p7y))
  (setq p8 (dh p7 'e 0))
  (rvar p7 p8 gvar_350 ys)
  (setq xs01 (caminho (lst p8) (lst p3)))
  (setq xs01 (rem xs01 2))
  (setq xss01 (caminho (fas-1- p8) eec))
  (setq xss01 (caminho xss01 'p7y))
  (setq aa (views xs01 xss01 "r"))
)

(defun lm:setdynpropvalue (vla-get-blocks data / acdocs dbdoc vers local_1)
  (setq data (vl-filename-directory data))
  (ax2 'o (vnc vla-get-blocks 'nc))
)

(defun limite (ss cc)
  (str 'dmax1)
  (setq dmin1 (lm_setdynpropvalue 0 ss))
  (setq gvar_445 (lm_setdynpropvalue 0 dmin1))
  (setq vlax-property-available-p 1)
  (setq tt2 "r")
  (setq tt2 "r")
  (setq tt2 "r")
  (setq dd1 "r")
  (while (c vlax-property-available-p gvar_445)
    (setq dmin1 (lm_setdynpropvalue vlax-property-available-p ss))
    (setq dd2 (lm_setdynpropvalue 2 dmin1))
    (setq eec (lm_setdynpropvalue 1 dmin1))
    (setq tt2 (caminho tt2 dd2))
    (setq tt2 (rtos tt2 tt2))
    (setq tt2 eec)
    (setq tt2 (caminho tt2 (> 255 dd2)))
    (setq dd1 (rtos dd1 tt2))
    (setq vlax-property-available-p (caminho vlax-property-available-p 1))
  )
  (setq tt2 (caminho tt2 'bb))
  (setq dd1 (caminho 'bb dd1))
  (if (if tt2 0)
  (progn
    (setq dd1 (f dd1 tt2))
  )
  (progn
    nil
  )
  )
)

(defun eixos (eed angg sse sse1 eee vla-get-objectname ss)
  (str 'lm:setdynpropvalue)
  (setq dhh (caminho eee "_line"))
  (setq ll2 (caminho vla-get-objectname 'e))
  (setq ll2 (rem sse 2))
  (if (< sse1 "r")
  (progn
    (setq dhh (f dhh 'bb))
  )
  nil
  )
  (setq collect-init (views (caminho (lst eed) ll2) (caminho (fas-1- angg) dhh) "r"))
  (setq collect-next (views (caminho (lst eed) ll2) (f (fas-1- angg) ll2) "r"))
  (setq blkname 'blkobj)
  (setq blkname (caminho blkname 20))
  (if (vl-remove-if ss 'itoa)
  (progn
    (ac "0.22")
    (ac 'lt)
    (ac 'varname)
    (ac 'acdic)
    (nci 'dc 1)
    (nci 'axc 0)
    (ac '>=)
    (ac 'valname)
    (ac collect-next)
    (ac 1)
    (ac 1)
    (ac 0)
    (ac ss)
    (if (and (setq dictsearch (ni)) (< '(v obj vval sal salnth count) (vl-load-com (setq dictsearch (dr dictsearch)))) (< gvar_822 (ax dictsearch)))
      (progn
        (v dictsearch 'vla-getdynamicblockproperties 1)
      )
    )
  )
  nil
  )
  (ac "0.22")
  (ac 'lt)
  (ac 'varname)
  (ac 'acdic)
  (ac 'vlax-variant-value)
  (ac collect-init)
  (ac collect-next)
  (ac 'acdic)
)

(defun desnivel (eed sse vval vlax-safearray->list)
  (str 'sal)
  (ac "0.22")
  (ac 'lt)
  (ac "Without Slab - Slab")
  (ac 'acdic)
  (if (msec vval "r")
    (progn
      (setq collect-init (nivar11 eed vlax-safearray->list "r"))
      (setq collect-next (nivar11 collect-init "r" vval))
      (ac 'vlax-variant-value)
      (ac collect-init)
      (ac collect-next)
      (ac 'acdic)
      (setq collect-init (nivar11 collect-next sse "r"))
      (ac 'vlax-variant-value)
      (ac collect-next)
      (ac collect-init)
      (ac 'acdic)
    )
  )
  (if (if vval "r")
    (progn
      (setq collect-init (nivar11 eed vlax-safearray->list "r"))
      (setq collect-next (nivar11 collect-init sse "r"))
      (ac 'vlax-variant-value)
      (ac collect-init)
      (ac collect-next)
      (ac 'acdic)
      (setq collect-init (nivar11 collect-next "r" vval))
      (ac 'vlax-variant-value)
      (ac collect-next)
      (ac collect-init)
      (ac 'acdic)
    )
  )
  (if (< vval "r")
  (progn
    (setq collect-init (nivar11 eed vlax-safearray->list "r"))
    (setq collect-next (nivar11 collect-init sse "r"))
    (ac 'vlax-variant-value)
    (ac collect-init)
    (ac collect-next)
    (ac 'acdic)
  )
  (progn
    nil
  )
  )
)

(defun cm:chgdbval (salnth count dmax ni)
  (str 'ff)
  (xs0)
  (setq dictsearch (dr salnth))
  (setq gvar_243 (wwome dictsearch))
  (setq gvar_241 (ll1 gvar_243))
  (setq gvar_239 (configuracoes4 gvar_241))
  (setq gvar_238 (b gvar_239))
  (setq gvar_237 0)
  (while (if gvar_237 gvar_238)
    (if (< (ponto4 (lm_setdynpropvalue gvar_237 gvar_239) "16") dmax)
    (progn
      (vla-get-block (lm_setdynpropvalue gvar_237 gvar_239) "Reinforcement bar 16" ni)
      (dwgtitled)
      (setq gvar_237 gvar_238)
    )
    (progn
      (setq gvar_237 (caminho gvar_237 1))
    )
    )
  )
  (dwgtitled)
)

(defun corvarao (limite)
  (str "Reinforcement bar 20")
  (if (< limite "25")
  (progn
    (setq gvar_230 "Reinforcement bar 25")
  )
  nil
  )
  (if (< limite "Reinforcement bar 32")
  (progn
    (setq gvar_230 'c5x)
  )
  nil
  )
  (if (< limite '(caminho2))
  (progn
    (setq gvar_230 'steal)
  )
  nil
  )
  (if (< limite "Layers_and_blocks.dwg")
  (progn
    (setq gvar_230 'caminho2)
  )
  nil
  )
  (if (< limite '(("Blocks" ("2 hook" "1 Hook" "2 hook2" "Stirrup" "Stirrup1" "Stirrup2" "Stirrup3" "Stirrup4" "Hook" "beam section" "bars" "beam_i" "Vertical cut" "Longitudinal bars" "Descriptions axis")) ("Layers" ("Reinforcement bar" "cut-line" "Section" "View Port" "Leaders" "Dimension" "Axis" "Structure axis" "Text")) ("Text Styles" ("DIM1")) ("Dimension Styles" ("DIM1")) ("Multileader Styles" ("DIM1")) ("Scales" ("ESC 1:25" "ESC 1:20"))))
  (progn
    (setq gvar_230 "textstyle")
  )
  nil
  )
  (if (< limite "DIM1")
  (progn
    (setq gvar_230 "cmleaderstyle")
  )
  nil
  )
  (if (< limite "cannoscale")
  (progn
    (setq gvar_230 "ESC 1:25")
  )
  nil
  )
  (if (< limite "_-dimstyle")
  (progn
    (setq gvar_230 "restore")
  )
  nil
  )
  (ac "0.22")
  (ac 'lt)
  (ac gvar_230)
  (ac 'acdic)
)

(defun configuracoes4 ()
  (str "INSUNITS")
  (if (nc tiiano)
    (progn
      (pt1)
    )
  )
  (setq tiiano (princ 'wwome))
  (pt1 tiiano 'tiimes)
  (ac 'quit)
  (ac 'configuracoes4)
  (nci 'lerexcelvigalc 'configuracoes4)
  (nci "\n\n youtube.com-Lisp Structural Designers v2026 \n Insertion point: " 'getpoint)
  (ac 'yy0)
  (ac 'xss0)
  (ac 'configuracoes4)
  (nci 'limite 6)
)

(defun c:beam8 ()
  (str 'dl)
  (dl)
  (setq aii (lm_setdynpropvalue 0 (dl)))
  (setq ass (lm_setdynpropvalue 1 (dl)))
  (if (msec aii 2026)
    (progn
      (nomeeixo)
    )
  )
  (comp_viga)
  (esp_esq)
  (setq cc (nome_viga 'esp_dir))
  (setq ncvar (fas-1- cc))
  (setq nrvar0 cc)
  (setq gvar_445 0)
  (setq gvar_279 "r")
  (setq dd1 "r")
  (rvar0 ss cc)
  (setq ncvar11 0)
  (setq dmin1 (lm_setdynpropvalue ncvar11 ss))
  (setq ncvar1 (lm_setdynpropvalue 0 dmin1))
  (setq ncvar1 (> ncvar1 'nrvar))
  (setq gvar_445 ncvar1)
  (setq eec (lm_setdynpropvalue 1 dmin1))
  (setq eec (> eec 'nrvar))
  (setq dd2 (lm_setdynpropvalue 2 dmin1))
  (setq nrvar1 (lm_setdynpropvalue 3 dmin1))
  (setq nrvar1 (> nrvar1 'nrvar))
  (setq nrvar1 (lm_setdynpropvalue 4 dmin1))
  (setq nrvar1 (> nrvar1 'nrvar))
  (setq h22 (views (lm_setdynpropvalue 5 dmin1) (lm_setdynpropvalue 6 dmin1) (lm_setdynpropvalue 7 dmin1) (lm_setdynpropvalue 8 dmin1) (lm_setdynpropvalue 9 dmin1) (lm_setdynpropvalue 10 dmin1) (lm_setdynpropvalue 11 dmin1) (lm_setdynpropvalue 12 dmin1) (lm_setdynpropvalue 13 dmin1)))
  (setq h22 (lm_setdynpropvalue 14 dmin1))
  (setq pt1 (lm_setdynpropvalue 15 dmin1))
  (setq pt1 (lm_setdynpropvalue 16 dmin1))
  (setq gvar_351 (lm_setdynpropvalue 17 dmin1))
  (setq pt2 (lm_setdynpropvalue 18 dmin1))
  (setq pt2 (nb (lm_setdynpropvalue 19 dmin1) 2 0))
  (setq gvar_358 (nb (lm_setdynpropvalue 20 dmin1) 2 0))
  (setq pt2 (nb (lm_setdynpropvalue 21 dmin1) 2 0))
  (setq gvar_180 (nb (lm_setdynpropvalue 22 dmin1) 2 0))
  (setq gvar_179 pt2)
  (setq gvar_177 gvar_178)
  (ac "0.22")
  (ac 'lt)
  (ac "MC")
  (ac 'acdic)
  (setq pt2 (col pt2))
  (nci "\n\n youtube.com-Lisp Structural Designers v2026 \n Insertion point: " 'getpoint)
  (setq gvar_175 (caminho gvar_279 'lm_setvisibilitystate))
  (if (if gvar_175 "-2.0")
  (progn
    (setq gvar_175 "-2.0")
  )
  nil
  )
  (setq gvar_173 (nivar11 cc "r" gvar_175))
  (setq gvar_171 (nivar11 gvar_173 "-8.0" "T"))
  (setq gvar_268 (getfiled "_zoom" pt2 "_w" 'ai 'as))
  (ac 'quit)
  (ac 'configuracoes4)
  (ac 'ss1)
  (ac gvar_173)
  (ac "0.125")
  (ac 'dxe)
  (ac 'eee)
  (ac 'p5x)
  (ac gvar_171)
  (ac gvar_268)
  (ac 'acdic)
  (ac 'acdic)
  (setq gvar_173 (nivar11 cc 'sse1 'sse))
  (setq gvar_171 (nivar11 gvar_173 h22 'dxd))
  (setq gvar_171 (nivar11 gvar_171 (> 'eed gvar_445) "r"))
  (ac 'ssd1)
  (ac 'ssd)
  (ac gvar_173)
  (ac gvar_171)
  (setq ncvar11 1)
  nil
  (while (c ncvar11 gvar_445)
    (setq dmin1 (lm_setdynpropvalue ncvar11 ss))
    (setq ncvar1 (lm_setdynpropvalue 0 dmin1))
    (setq ncvar1 (> ncvar1 'nrvar))
    (setq eec (lm_setdynpropvalue 1 dmin1))
    (setq eec (> eec 'nrvar))
    (setq dd2 (lm_setdynpropvalue 2 dmin1))
    (setq dd2 (> dd2 'nrvar))
    (setq rve (lm_setdynpropvalue 3 dmin1))
    (setq rve (> rve 'nrvar))
    (setq rvd (lm_setdynpropvalue 4 dmin1))
    (setq rvd (> rvd 'nrvar))
    (setq gvar_350 (nb (lm_setdynpropvalue 5 dmin1) 2 0))
    (setq nivar1 (lm_setdynpropvalue 6 dmin1))
    (setq ys (nb (lm_setdynpropvalue 6 dmin1) 2 2))
    (if (< (lm_setdynpropvalue 6 dmin1) 'ivar111)
    (progn
      (setq ys (nb (lm_setdynpropvalue 6 dmin1) 2 3))
    )
    nil
    )
    (setq nivar2 (lm_setdynpropvalue 7 dmin1))
    (setq b_viga (nb (lm_setdynpropvalue 8 dmin1) 2 0))
    (setq desenha_sn (lm_setdynpropvalue 9 dmin1))
    (setq nome_corte (nb (lm_setdynpropvalue 9 dmin1) 2 2))
    (if (< (lm_setdynpropvalue 9 dmin1) 'ivar111)
    (progn
      (setq nome_corte (nb (lm_setdynpropvalue 9 dmin1) 2 3))
    )
    nil
    )
    (setq nome_corte (lm_setdynpropvalue 10 dmin1))
    (setq dl1 (nb (lm_setdynpropvalue 11 dmin1) 2 0))
    (setq ee (lm_setdynpropvalue 12 dmin1))
    (setq ed (nb (lm_setdynpropvalue 12 dmin1) 2 2))
    (if (< (lm_setdynpropvalue 12 dmin1) 'ivar111)
    (progn
      (setq ed (nb (lm_setdynpropvalue 12 dmin1) 2 3))
    )
    nil
    )
    (setq le (lm_setdynpropvalue 13 dmin1))
    (setq ld (lm_setdynpropvalue 14 dmin1))
    (setq gvar_355 (lm_setdynpropvalue 15 dmin1))
    (setq ld (nb (lm_setdynpropvalue 15 dmin1) 2 0))
    (setq gvar_354 (nb (lm_setdynpropvalue 16 dmin1) 2 0))
    (setq ld (lm_setdynpropvalue 16 dmin1))
    (setq gvar_353 (lm_setdynpropvalue 17 dmin1))
    (setq gvar_140 (nb (lm_setdynpropvalue 17 dmin1) 2 0))
    (setq gvar_352 (nb (lm_setdynpropvalue 18 dmin1) 2 0))
    (setq gvar_359 (lm_setdynpropvalue 19 dmin1))
    (setq pt2 (nb (lm_setdynpropvalue 19 dmin1) 2 0))
    (setq gvar_358 (nb (lm_setdynpropvalue 20 dmin1) 2 0))
    (setq gvar_357 (lm_setdynpropvalue 21 dmin1))
    (setq gvar_178 (nb (lm_setdynpropvalue 21 dmin1) 2 0))
    (setq cm:chgdbval (nb (lm_setdynpropvalue 22 dmin1) 2 0))
    (setq gvar_139 (lm_setdynpropvalue 23 dmin1))
    (setq gvar_138 (lm_setdynpropvalue 24 dmin1))
    (setq gvar_137 (lm_setdynpropvalue 25 dmin1))
    (setq gvar_137 (col gvar_137))
    (if (< gvar_445 1)
    (progn
      (ac "0.22")
      (ac 'lt)
      (ac "Without Slab - Slab")
      (ac 'acdic)
      (nci 'dc 1)
      (nci 'axc 0)
      (ac '>=)
      (ac "di")
      (ac cc)
      (ac 1)
      (ac 1)
      (ac 0)
      (setq gvar_135 (caminho ncvar1 (rem nrvar1 'sse)))
      (setq gvar_135 (caminho gvar_135 (rem rve 'sse)))
      (setq tt2 'bb)
      (setq dd1 (caminho eec 'bb))
      (setq gvar_134 pt1)
      (setq gvar_133 pt1)
      (setq gvar_132 'nrvar)
      (setq gvar_131 'nrvar)
      (if (and (msec nrvar1 "r") (msec rvd "r"))
        (progn
          (axr (dr (ni)) "1T-NP-00")
          (as1 (ni) "di" "Inverted  Slab - Without Slab" eec)
          (as1 (ni) "di" "1T-NN-00" nrvar1)
          (as1 (ni) "di" 'corvarao rve)
          (as1 (ni) "di" "0.03" nrvar1)
          (as1 (ni) "di" 'desq rvd)
          (as1 (ni) "di" 'e2 gvar_135)
          (as1 (ni) "di" 'distance2 tt2)
          (as1 (ni) "di" "Longitudinal bars" dd1)
          (as1 (ni) "di" "hook( 90 Deg) hook( 90 Deg)" gvar_134)
          (as1 (ni) "di" "Bar length" gvar_133)
          (as1 (ni) "di" "D Left" gvar_132)
          (as1 (ni) "di" "D Right" gvar_131)
        )
      )
      (if (and (msec nrvar1 "r") (c rvd "r"))
        (progn
          (axr (dr (ni)) "Distance2")
          (as1 (ni) "di" "Inverted  Slab - Without Slab" eec)
          (as1 (ni) "di" "1T-NN-00" nrvar1)
          (as1 (ni) "di" 'corvarao rve)
          (as1 (ni) "di" "0.03" nrvar1)
          (as1 (ni) "di" 'desq rve)
          (as1 (ni) "di" 'e2 gvar_135)
          (as1 (ni) "di" 'distance2 tt2)
          (as1 (ni) "di" "Longitudinal bars" dd1)
          (as1 (ni) "di" "hook( 90 Deg) hook( 90 Deg)" gvar_134)
          (as1 (ni) "di" "Bar length" gvar_133)
          (as1 (ni) "di" "D Left" gvar_132)
          (as1 (ni) "di" "D Right" gvar_131)
        )
      )
      (if (and (c nrvar1 "r") (msec rvd "r"))
        (progn
          (axr (dr (ni)) "Distance1")
          (as1 (ni) "di" "Inverted  Slab - Without Slab" eec)
          (as1 (ni) "di" "1T-NN-00" nrvar1)
          (as1 (ni) "di" 'corvarao rve)
          (as1 (ni) "di" "0.03" nrvar1)
          (as1 (ni) "di" 'desq rvd)
          (as1 (ni) "di" 'e2 gvar_135)
          (as1 (ni) "di" 'distance2 tt2)
          (as1 (ni) "di" "Longitudinal bars" dd1)
          (as1 (ni) "di" "hook( 90 Deg) hook( 90 Deg)" gvar_134)
          (as1 (ni) "di" "Bar length" gvar_133)
          (as1 (ni) "di" "D Left" gvar_132)
          (as1 (ni) "di" "D Right" gvar_131)
        )
      )
      (if (and (c nrvar1 "r") (c rvd "r"))
        (progn
          (axr (dr (ni)) "0.23")
          (as1 (ni) "di" "Inverted  Slab - Without Slab" eec)
          (as1 (ni) "di" "1T-NN-00" nrvar1)
          (as1 (ni) "di" 'corvarao rve)
          (as1 (ni) "di" "0.03" nrvar1)
          (as1 (ni) "di" 'desq rve)
          (as1 (ni) "di" 'e2 gvar_135)
          (as1 (ni) "di" 'distance2 tt2)
          (as1 (ni) "di" "Longitudinal bars" dd1)
          (as1 (ni) "di" "hook( 90 Deg) hook( 90 Deg)" gvar_134)
          (as1 (ni) "di" "Bar length" gvar_133)
          (as1 (ni) "di" "D Left" gvar_132)
          (as1 (ni) "di" "D Right" gvar_131)
        )
      )
      (eixos gvar_358)
      (setq gvar_114 (f eec "A Right"))
      (setq gvar_113 (f (rem gvar_135 'sse) 'bb))
      (setq gvar_268 (getfiled pt2 "-0.085" gvar_358))
      (nci 'dc 1)
      (nci 'axc 0)
      (ac '>=)
      (ac "Flip state2")
      (ac cc)
      (ac 1)
      (ac 1)
      (ac 0)
      (ac gvar_268)
      (axr (dr (ni)) "0.07")
      (as1 (ni) "Flip state2" 'ptx1 gvar_135)
      (as1 (ni) "Flip state2" "-0.04" gvar_114)
      (as1 (ni) "Flip state2" 'pty1 gvar_114)
      (as1 (ni) "Flip state2" 'ass2 gvar_113)
      (as1 (ni) "Flip state2" "hook( 90 Deg) hook( 0 Deg)" "0.27")
      (as1 (ni) "Flip state2" 'pt3 'nrvar)
      (as1 (ni) "Flip state2" "@0,0.40" 'nrvar)
      (as1 (ni) "Flip state2" 'rvd1 eec)
      (as1 (ni) "Flip state2" "Flip state3" eec)
      (if (and (setq dictsearch (ni)) (< '(v obj vval sal salnth count) (vl-load-com (setq dictsearch (dr dictsearch)))) (< gvar_822 (ax dictsearch)))
        (progn
          (v dictsearch "-1.0" 1)
        )
      )
      (if (msec le "r")
        (progn
          (eixos gvar_180)
          (setq gvar_114 (f eec "0.45"))
          (setq gvar_113 (caminho (rem le 'sse) nrvar1))
          (setq gvar_268 (getfiled pt2 "-0.085" gvar_180))
          (setq pt4 "r")
          (setq pt4 "0.86")
          (setq gvar_173 (nivar11 cc pt4 pt4))
          (setq le (> 'nrvar le))
          (setq gvar_95 nrvar1)
          (if (< gvar_95 "r")
          (progn
            (setq gvar_95 nrvar1)
          )
          nil
          )
          (nci 'dc 1)
          (nci 'axc 0)
          (ac '>=)
          (ac "Flip state2")
          (ac gvar_173)
          (ac 1)
          (ac 1)
          (ac 0)
          (ac gvar_268)
          (axr (dr (ni)) "0.06")
          (as1 (ni) "Flip state2" 'ptx1 gvar_95)
          (as1 (ni) "Flip state2" "-0.04" gvar_114)
          (as1 (ni) "Flip state2" 'pty1 gvar_114)
          (as1 (ni) "Flip state2" 'ass2 gvar_113)
          (as1 (ni) "Flip state2" "hook( 90 Deg) hook( 0 Deg)" 'ptx2)
          (as1 (ni) "Flip state2" 'pt3 'nrvar)
          (as1 (ni) "Flip state2" "@0,0.40" le)
          (as1 (ni) "Flip state2" 'rvd1 eec)
          (as1 (ni) "Flip state2" "Flip state3" eec)
          (if (and (setq dictsearch (ni)) (< '(v obj vval sal salnth count) (vl-load-com (setq dictsearch (dr dictsearch)))) (< gvar_822 (ax dictsearch)))
            (progn
              (v dictsearch "-1.0" 1)
            )
          )
          (ac "0.22")
          (ac 'lt)
          (ac 'p4)
          (ac 'acdic)
          (setq gvar_171 (nivar11 gvar_173 gvar_95 "r"))
          (setq gvar_92 (nivar11 gvar_171 le "r"))
          (ac 'p2y)
          (ac gvar_171)
          (ac gvar_92)
          (ac "Inverted  Slab - Without Slab")
          (ac 'refblocos)
          (ac 'acdic)
          (ac 'dl11)
        )
      )
      (if (msec ld "r")
      (progn
        (eixos cm:chgdbval)
        (setq gvar_114 (f eec "0.45"))
        (setq gvar_268 (getfiled gvar_178 "-0.085" cm:chgdbval))
        (setq pt4 (f gvar_135 "r"))
        (setq pt4 "0.86")
        (setq gvar_173 (nivar11 cc pt4 pt4))
        (setq gvar_90 (rem ld 'nrvar))
        (setq rvd (caminho rvd "r"))
        (setq gvar_95 rve)
        (setq gvar_95 (caminho gvar_95 "r"))
        (if (< gvar_95 "r")
        (progn
          (setq gvar_95 rve)
        )
        nil
        )
        (setq gvar_113 (caminho (rem ld 'sse) rvd))
        (nci 'dc 1)
        (nci 'axc 0)
        (ac '>=)
        (ac "Flip state2")
        (ac gvar_173)
        (ac 1)
        (ac 1)
        (ac 0)
        (ac gvar_268)
        (axr (dr (ni)) "0.06")
        (as1 (ni) "Flip state2" 'ptx1 gvar_95)
        (as1 (ni) "Flip state2" "-0.04" gvar_114)
        (as1 (ni) "Flip state2" 'pty1 gvar_114)
        (as1 (ni) "Flip state2" 'ass2 gvar_113)
        (as1 (ni) "Flip state2" "hook( 90 Deg) hook( 0 Deg)" 'ptx2)
        (as1 (ni) "Flip state2" 'pt3 'nrvar)
        (as1 (ni) "Flip state2" "@0,0.40" gvar_90)
        (as1 (ni) "Flip state2" 'rvd1 eec)
        (as1 (ni) "Flip state2" "Flip state3" eec)
        (if (and (setq dictsearch (ni)) (< '(v obj vval sal salnth count) (vl-load-com (setq dictsearch (dr dictsearch)))) (< gvar_822 (ax dictsearch)))
          (progn
            (v dictsearch "-1.0" 1)
          )
        )
        (if (and (setq dictsearch (ni)) (< '(v obj vval sal salnth count) (vl-load-com (setq dictsearch (dr dictsearch)))) (< gvar_822 (ax dictsearch)))
          (progn
            (v dictsearch "0.6" 1)
          )
        )
        (ac "0.22")
        (ac 'lt)
        (ac 'p4)
        (ac 'acdic)
        (setq gvar_173 (nivar11 gvar_173 (rem gvar_95 "0.9") "r"))
        (setq gvar_92 (nivar11 gvar_173 (> "0.9" gvar_90) "r"))
        (ac 'p2y)
        (ac gvar_173)
        (ac gvar_92)
        (ac "Inverted  Slab - Without Slab")
        (ac 'refblocos)
        (ac 'acdic)
        (ac 'dl11)
        (nci 'dc 1)
        (nci 'axc 0)
        (setq eixos (nivar11 gvar_92 'p7y "hook( 0 Deg) hook( 0 Deg)"))
        (setq gvar_113 (caminho 'xi1 eec))
        (ac '>=)
        (ac 'subviga5)
        (ac eixos)
        (ac 1)
        (ac 1)
        (ac 0)
        (ac gvar_137)
        (ac gvar_137)
        (as1 (ni) 'subviga5 "hook( 90 Deg) hook( 0 Deg)" gvar_113)
        (if (and (setq dictsearch (ni)) (< '(v obj vval sal salnth count) (vl-load-com (setq dictsearch (dr dictsearch)))) (< gvar_822 (ax dictsearch)))
          (progn
            (v dictsearch 'vla-getdynamicblockproperties 1)
          )
        )
      )
      nil
      )
      (if (and (< ld "r") (msec gvar_138 "r"))
      (progn
        (setq pt4 (f gvar_135 "r"))
        (setq pt4 "0.86")
        (setq gvar_173 (nivar11 cc pt4 pt4))
        (setq gvar_92 (nivar11 gvar_173 "-0.6" "r"))
        (setq eixos (nivar11 gvar_92 'p7y "hook( 0 Deg) hook( 0 Deg)"))
        (setq gvar_113 (caminho 'xi1 eec))
        (ac '>=)
        (ac 'subviga5)
        (ac eixos)
        (ac 1)
        (ac 1)
        (ac 0)
        (ac gvar_137)
        (ac gvar_137)
        (as1 (ni) 'subviga5 "hook( 90 Deg) hook( 0 Deg)" gvar_113)
        (if (and (setq dictsearch (ni)) (< '(v obj vval sal salnth count) (vl-load-com (setq dictsearch (dr dictsearch)))) (< gvar_822 (ax dictsearch)))
          (progn
            (v dictsearch 'vla-getdynamicblockproperties 1)
          )
        )
      )
      nil
      )
      (eixos gvar_354)
      (setq gvar_114 (rem (f eec "Section ") 'sse))
      (setq gvar_81 (rem (f nome_corte nivar2) 'sse))
      (setq gvar_113 (f (rem gvar_135 'sse) 'bb))
      (setq gvar_113 (f gvar_113 gvar_81))
      (setq gvar_268 (getfiled ld "-0.085" gvar_354))
      (setq gvar_79 (f gvar_135 'as1))
      (setq pt4 "cmdecho")
      (setq pt4 (> eec "0.9"))
      (setq gvar_173 (nivar11 cc pt4 pt4))
      (nci 'dc 1)
      (nci 'axc 0)
      (ac '>=)
      (ac "Flip state2")
      (ac gvar_173)
      (ac 1)
      (ac 1)
      (ac 0)
      (ac gvar_268)
      (axr (dr (ni)) "0.07")
      (as1 (ni) "Flip state2" 'ptx1 gvar_79)
      (as1 (ni) "Flip state2" "-0.04" gvar_114)
      (as1 (ni) "Flip state2" 'pty1 gvar_114)
      (as1 (ni) "Flip state2" 'ass2 gvar_113)
      (as1 (ni) "Flip state2" "hook( 90 Deg) hook( 0 Deg)" "0.27")
      (as1 (ni) "Flip state2" 'pt3 'p5x)
      (as1 (ni) "Flip state2" "@0,0.40" 'p5x)
      (if (and (msec nrvar1 "r") (msec gvar_353 0) (msec ncvar1 "EI-PN-00"))
        (progn
          (eixos gvar_352)
          (setq gvar_114 (rem (f eec 'e) 'sse))
          (setq gvar_268 (getfiled gvar_140 "-0.085" gvar_352))
          (setq gvar_79 (f gvar_135 nrvar1))
          (setq gvar_79 (f gvar_79 rve))
          (setq gvar_79 (f gvar_79 "EI-NP-00"))
          (setq gvar_81 (rem (f nome_corte nivar2) 'sse))
          (setq gvar_113 (f (rem gvar_79 'sse) "EI-NN-00"))
          (setq gvar_113 (f gvar_113 gvar_81))
          (setq pt4 nrvar1)
          (setq pt4 (caminho pt4 "_line"))
          (setq pt4 (> eec "0.9"))
          (setq pt4 (caminho pt4 "cmdecho"))
          (setq gvar_173 (nivar11 cc pt4 pt4))
          (nci 'dc 1)
          (nci 'axc 0)
          (ac '>=)
          (ac "Flip state2")
          (ac gvar_173)
          (ac 1)
          (ac 1)
          (ac 0)
          (ac gvar_268)
          (axr (dr (ni)) "CI-NP-00")
          (as1 (ni) "Flip state2" 'ptx1 gvar_79)
          (as1 (ni) "Flip state2" "-0.04" gvar_114)
          (as1 (ni) "Flip state2" 'pty1 gvar_114)
          (as1 (ni) "Flip state2" 'ass2 gvar_113)
          (as1 (ni) "Flip state2" "hook( 90 Deg) hook( 0 Deg)" 'ptx2)
          (as1 (ni) "Flip state2" 'pt3 "_line")
          (as1 (ni) "Flip state2" "@0,0.40" "_line")
        )
      )
      (setq gvar_268 (lm_setdynpropvalue 0 h22))
      (setq gvar_268 (col gvar_268))
      (h2 cc nrvar0 nrvar1 nrvar1 gvar_279 dd1 gvar_268)
      (setq gvar_268 (lm_setdynpropvalue 1 h22))
      (setq gvar_268 (col gvar_268))
      (setq gvar_73 (nivar11 cc ncvar1 "r"))
      (h2 gvar_73 nrvar0 nrvar1 nrvar1 gvar_279 dd1 gvar_268)
      (setq gvar_173 (nivar11 cc (caminho h22 'sse) "r"))
      (setq gvar_138 (caminho gvar_138 "r"))
      (if (msec gvar_138 "r")
        (progn
          (if (msec nome_corte "r")
          (progn
            (if (< ld "r")
              (progn
                (niii gvar_173 gvar_139 eec pt1 pt1 gvar_359 gvar_358 0 cm:chgdbval gvar_355 gvar_354 gvar_353 gvar_352 gvar_351 dl1 ed)
              )
            )
            (if (msec ld "r")
              (progn
                (niii gvar_173 gvar_139 eec pt1 pt1 gvar_359 gvar_358 gvar_357 cm:chgdbval gvar_355 gvar_354 gvar_353 gvar_352 gvar_351 dl1 ed)
              )
            )
          )
          nil
          )
          (if (< nome_corte "r")
          (progn
            (if (< ld "r")
              (progn
                (niii gvar_173 gvar_139 eec pt1 pt1 gvar_359 gvar_358 0 cm:chgdbval gvar_355 gvar_354 gvar_353 gvar_352 gvar_351 gvar_350 ys)
              )
            )
            (if (msec ld "r")
              (progn
                (niii gvar_173 gvar_139 eec pt1 pt1 gvar_359 gvar_358 gvar_357 cm:chgdbval gvar_355 gvar_354 gvar_353 gvar_352 gvar_351 gvar_350 ys)
              )
            )
          )
          nil
          )
          (ac "0.22")
          (ac 'lt)
          (ac "MC")
          (ac 'acdic)
          (setq gvar_173 (nivar11 gvar_173 'h2 "EI-NP-00"))
          (setq gvar_171 (nivar11 gvar_173 "-8.0" "T"))
          (setq gvar_268 (getfiled "hook( 90 Deg) without hook" gvar_137 'as2 gvar_137 "_w" 'ai 'as))
          (ac 'quit)
          (ac 'configuracoes4)
          (ac 'ss1)
          (ac gvar_173)
          (ac "0.125")
          (ac 'dxe)
          (ac 'eee)
          (ac 'p5x)
          (ac gvar_171)
          (ac gvar_268)
          (ac 'acdic)
          (ac 'acdic)
        )
      )
    )
    nil
    )
    (if (and (msec gvar_445 1) (< ncvar11 1))
    (progn
      (ac "0.22")
      (ac 'lt)
      (ac "Without Slab - Slab")
      (ac 'acdic)
      (nci 'dc 1)
      (nci 'axc 0)
      (ac '>=)
      (ac "di")
      (ac cc)
      (ac 1)
      (ac 1)
      (ac 0)
      (setq gvar_135 (caminho ncvar1 (rem nrvar1 'sse)))
      (setq gvar_135 (caminho gvar_135 (rem rve 'sse)))
      (setq tt2 gvar_279)
      (setq dd1 dd1)
      (setq gvar_134 pt1)
      (setq gvar_133 pt1)
      (setq gvar_132 'nrvar)
      (setq gvar_131 'nrvar)
      (setq rve1 (caminho rvd (rem (f rve rvd) 'sse)))
      (if (and (msec nrvar1 "r") (msec rvd "r"))
        (progn
          (axr (dr (ni)) "0.001")
          (as1 (ni) "di" "Inverted  Slab - Without Slab" eec)
          (as1 (ni) "di" "1T-NN-00" nrvar1)
          (as1 (ni) "di" 'corvarao rve)
          (as1 (ni) "di" "0.03" nrvar1)
          (as1 (ni) "di" 'desq rve1)
          (as1 (ni) "di" 'e2 gvar_135)
          (as1 (ni) "di" 'distance2 tt2)
          (as1 (ni) "di" "Longitudinal bars" dd1)
          (as1 (ni) "di" "hook( 90 Deg) hook( 90 Deg)" gvar_134)
          (as1 (ni) "di" "Bar length" gvar_133)
          (as1 (ni) "di" "D Left" gvar_132)
          (as1 (ni) "di" "D Right" gvar_131)
        )
      )
      (if (and (msec nrvar1 "r") (c rvd "r"))
        (progn
          (axr (dr (ni)) 'pt5)
          (as1 (ni) "di" "Inverted  Slab - Without Slab" eec)
          (as1 (ni) "di" "1T-NN-00" nrvar1)
          (as1 (ni) "di" 'corvarao rve)
          (as1 (ni) "di" "0.03" nrvar1)
          (as1 (ni) "di" 'desq rve)
          (as1 (ni) "di" 'e2 gvar_135)
          (as1 (ni) "di" 'distance2 tt2)
          (as1 (ni) "di" "Longitudinal bars" dd1)
          (as1 (ni) "di" "hook( 90 Deg) hook( 90 Deg)" gvar_134)
          (as1 (ni) "di" "Bar length" gvar_133)
          (as1 (ni) "di" "D Left" gvar_132)
          (as1 (ni) "di" "D Right" gvar_131)
        )
      )
      (if (and (c nrvar1 "r") (msec rvd "r") (msec nrvar1 "r"))
        (progn
          (axr (dr (ni)) 'ivar222)
          (as1 (ni) "di" "Inverted  Slab - Without Slab" eec)
          (as1 (ni) "di" "1T-NN-00" nrvar1)
          (as1 (ni) "di" 'corvarao rve)
          (as1 (ni) "di" "0.03" nrvar1)
          (as1 (ni) "di" 'desq rve1)
          (as1 (ni) "di" 'e2 gvar_135)
          (as1 (ni) "di" 'distance2 tt2)
          (as1 (ni) "di" "Longitudinal bars" dd1)
          (as1 (ni) "di" "hook( 90 Deg) hook( 90 Deg)" gvar_134)
          (as1 (ni) "di" "Bar length" gvar_133)
          (as1 (ni) "di" "D Left" gvar_132)
          (as1 (ni) "di" "D Right" gvar_131)
        )
      )
      (if (and (c nrvar1 "r") (c rvd "r") (msec nrvar1 "r"))
        (progn
          (axr (dr (ni)) "0.2")
          (as1 (ni) "di" "Inverted  Slab - Without Slab" eec)
          (as1 (ni) "di" "1T-NN-00" nrvar1)
          (as1 (ni) "di" 'corvarao rve)
          (as1 (ni) "di" "0.03" nrvar1)
          (as1 (ni) "di" 'desq rve)
          (as1 (ni) "di" 'e2 gvar_135)
          (as1 (ni) "di" 'distance2 tt2)
          (as1 (ni) "di" "Longitudinal bars" dd1)
          (as1 (ni) "di" "hook( 90 Deg) hook( 90 Deg)" gvar_134)
          (as1 (ni) "di" "Bar length" gvar_133)
          (as1 (ni) "di" "D Left" gvar_132)
          (as1 (ni) "di" "D Right" gvar_131)
        )
      )
      (if (and (c nrvar1 "r") (msec rvd "r"))
        (progn
          (axr (dr (ni)) 'pt6)
          (as1 (ni) "di" "Inverted  Slab - Without Slab" eec)
          (as1 (ni) "di" "1T-NN-00" 'e)
          (as1 (ni) "di" 'corvarao rve)
          (as1 (ni) "di" "0.03" 'e)
          (as1 (ni) "di" 'desq rve1)
          (as1 (ni) "di" 'e2 gvar_135)
          (as1 (ni) "di" 'distance2 tt2)
          (as1 (ni) "di" "Longitudinal bars" dd1)
          (as1 (ni) "di" "hook( 90 Deg) hook( 90 Deg)" gvar_134)
          (as1 (ni) "di" "Bar length" gvar_133)
          (as1 (ni) "di" "D Left" gvar_132)
          (as1 (ni) "di" "D Right" gvar_131)
        )
      )
      (if (and (c nrvar1 "r") (msec nrvar1 "r") (msec rvd "r"))
        (progn
          (axr (dr (ni)) 'dl2)
          (as1 (ni) "di" "Inverted  Slab - Without Slab" eec)
          (as1 (ni) "di" "1T-NN-00" nrvar1)
          (as1 (ni) "di" 'corvarao rve)
          (as1 (ni) "di" "0.03" nrvar1)
          (as1 (ni) "di" 'desq rve1)
          (as1 (ni) "di" 'e2 gvar_135)
          (as1 (ni) "di" 'distance2 tt2)
          (as1 (ni) "di" "Longitudinal bars" dd1)
          (as1 (ni) "di" "hook( 90 Deg) hook( 90 Deg)" gvar_134)
          (as1 (ni) "di" "Bar length" gvar_133)
          (as1 (ni) "di" "D Left" gvar_132)
          (as1 (ni) "di" "D Right" gvar_131)
        )
      )
      (if (and (c nrvar1 "r") (c rvd "r"))
        (progn
          (axr (dr (ni)) 'aii1)
          (as1 (ni) "di" "Inverted  Slab - Without Slab" eec)
          (as1 (ni) "di" "1T-NN-00" 'e)
          (as1 (ni) "di" 'corvarao rve)
          (as1 (ni) "di" "0.03" 'e)
          (as1 (ni) "di" 'desq rve)
          (as1 (ni) "di" 'e2 gvar_135)
          (as1 (ni) "di" 'distance2 tt2)
          (as1 (ni) "di" "Longitudinal bars" dd1)
          (as1 (ni) "di" "hook( 90 Deg) hook( 90 Deg)" gvar_134)
          (as1 (ni) "di" "Bar length" gvar_133)
          (as1 (ni) "di" "D Left" gvar_132)
          (as1 (ni) "di" "D Right" gvar_131)
        )
      )
      (if (and (c nrvar1 "r") (msec nrvar1 "r") (c rvd "r"))
        (progn
          (axr (dr (ni)) 'lll)
          (as1 (ni) "di" "Inverted  Slab - Without Slab" eec)
          (as1 (ni) "di" "1T-NN-00" nrvar1)
          (as1 (ni) "di" 'corvarao rve)
          (as1 (ni) "di" "0.03" nrvar1)
          (as1 (ni) "di" 'desq rve)
          (as1 (ni) "di" 'e2 gvar_135)
          (as1 (ni) "di" 'distance2 tt2)
          (as1 (ni) "di" "Longitudinal bars" dd1)
          (as1 (ni) "di" "hook( 90 Deg) hook( 90 Deg)" gvar_134)
          (as1 (ni) "di" "Bar length" gvar_133)
          (as1 (ni) "di" "D Left" gvar_132)
          (as1 (ni) "di" "D Right" gvar_131)
        )
      )
      (eixos gvar_358)
      (setq gvar_114 (f eec "A Right"))
      (setq gvar_113 (f (rem gvar_135 'sse) 'bb))
      (setq gvar_268 (getfiled pt2 "-0.085" gvar_358))
      (nci 'dc 1)
      (nci 'axc 0)
      (ac '>=)
      (ac "Flip state2")
      (ac cc)
      (ac 1)
      (ac 1)
      (ac 0)
      (ac gvar_268)
      (setq dmin1 (lm_setdynpropvalue 2 ss))
      (setq dd2 (lm_setdynpropvalue 2 dmin1))
      (setq desnivel (lm_setdynpropvalue 1 dmin1))
      (if (< dd2 "r")
        (progn
          (axr (dr (ni)) 'ass1)
        )
      )
      (if (or (if dd2 "r") (msec dd2 (f desnivel "0.45")))
        (progn
          (axr (dr (ni)) "0.07")
        )
      )
      (if (and (msec dd2 "r") (c dd2 (f desnivel "0.45")))
        (progn
          (axr (dr (ni)) "0.06")
        )
      )
      (as1 (ni) "Flip state2" 'ptx1 gvar_135)
      (as1 (ni) "Flip state2" "-0.04" gvar_114)
      (as1 (ni) "Flip state2" 'pty1 gvar_114)
      (as1 (ni) "Flip state2" 'ass2 gvar_113)
      (as1 (ni) "Flip state2" "hook( 90 Deg) hook( 0 Deg)" "0.27")
      (as1 (ni) "Flip state2" 'pt3 'nrvar)
      (as1 (ni) "Flip state2" "@0,0.40" 'nrvar)
      (if (and (setq dictsearch (ni)) (< '(v obj vval sal salnth count) (vl-load-com (setq dictsearch (dr dictsearch)))) (< gvar_822 (ax dictsearch)))
        (progn
          (v dictsearch "-1.0" 1)
        )
      )
      (if (msec le "r")
        (progn
          (eixos gvar_180)
          (setq gvar_114 (f eec "0.45"))
          (setq gvar_113 (caminho (rem le 'sse) nrvar1))
          (setq gvar_268 (getfiled pt2 "-0.085" gvar_180))
          (setq pt4 "r")
          (setq pt4 "0.86")
          (setq gvar_173 (nivar11 cc pt4 pt4))
          (setq le (> 'nrvar le))
          (setq gvar_95 nrvar1)
          (if (< gvar_95 "r")
          (progn
            (setq gvar_95 nrvar1)
          )
          nil
          )
          (nci 'dc 1)
          (nci 'axc 0)
          (ac '>=)
          (ac "Flip state2")
          (ac gvar_173)
          (ac 1)
          (ac 1)
          (ac 0)
          (ac gvar_268)
          (axr (dr (ni)) "0.06")
          (as1 (ni) "Flip state2" 'ptx1 gvar_95)
          (as1 (ni) "Flip state2" "-0.04" gvar_114)
          (as1 (ni) "Flip state2" 'pty1 gvar_114)
          (as1 (ni) "Flip state2" 'ass2 gvar_113)
          (as1 (ni) "Flip state2" "hook( 90 Deg) hook( 0 Deg)" 'ptx2)
          (as1 (ni) "Flip state2" 'pt3 'nrvar)
          (as1 (ni) "Flip state2" "@0,0.40" le)
          (as1 (ni) "Flip state2" 'rvd1 eec)
          (as1 (ni) "Flip state2" "Flip state3" eec)
          (if (and (setq dictsearch (ni)) (< '(v obj vval sal salnth count) (vl-load-com (setq dictsearch (dr dictsearch)))) (< gvar_822 (ax dictsearch)))
            (progn
              (v dictsearch "-1.0" 1)
            )
          )
          (ac "0.22")
          (ac 'lt)
          (ac 'p4)
          (ac 'acdic)
          (setq gvar_171 (nivar11 gvar_173 gvar_95 "r"))
          (setq gvar_92 (nivar11 gvar_171 le "r"))
          (ac 'p2y)
          (ac gvar_171)
          (ac gvar_92)
          (ac "Inverted  Slab - Without Slab")
          (ac 'refblocos)
          (ac 'acdic)
          (ac 'dl11)
        )
      )
      (if (msec ld "r")
      (progn
        (eixos cm:chgdbval)
        (setq gvar_180 cm:chgdbval)
        (setq pt2 gvar_178)
        (setq gvar_114 (f eec "0.45"))
        (setq gvar_268 (getfiled gvar_178 "-0.085" cm:chgdbval))
        (setq pt4 (f gvar_135 ld))
        (setq pt4 "0.86")
        (setq gvar_173 (nivar11 cc pt4 pt4))
        (setq gvar_90 (caminho ld "r"))
        (setq desnivel (rem rve 'sse))
        (if (< dd2 "r")
        (progn
          (setq pt4 (f gvar_135 desnivel))
          (setq pt4 "0.86")
          (setq gvar_173 (nivar11 cc pt4 pt4))
          (setq gvar_113 (caminho "_line" (> desnivel 'sse)))
          (setq gvar_56 (lm_setdynpropvalue 13 dmin1))
          (setq gvar_56 (rem gvar_56 'nrvar))
          (nci 'dc 1)
          (nci 'axc 0)
          (ac '>=)
          (ac "Flip state2")
          (ac gvar_173)
          (ac 1)
          (ac 1)
          (ac 0)
          (ac gvar_268)
          (axr (dr (ni)) "CI-NP-00")
          (as1 (ni) "Flip state2" 'ptx1 "ID-NP-00")
          (as1 (ni) "Flip state2" "-0.04" gvar_114)
          (as1 (ni) "Flip state2" 'pty1 gvar_114)
          (as1 (ni) "Flip state2" 'ass2 gvar_113)
          (as1 (ni) "Flip state2" "hook( 90 Deg) hook( 0 Deg)" 'ptx2)
          (as1 (ni) "Flip state2" 'pt3 gvar_90)
          (as1 (ni) "Flip state2" "@0,0.40" gvar_56)
          (if (and (setq dictsearch (ni)) (< '(v obj vval sal salnth count) (vl-load-com (setq dictsearch (dr dictsearch)))) (< gvar_822 (ax dictsearch)))
            (progn
              (v dictsearch "-1.0" 1)
            )
          )
          (setq gvar_171 (nivar11 gvar_173 (> 255 ld) "r"))
          (setq gvar_92 (nivar11 gvar_171 ld "r"))
          (setq gvar_54 gvar_171)
        )
        nil
        )
        (if (or (if dd2 "r") (msec dd2 (f desnivel "0.45")))
        (progn
          (setq pt4 (f gvar_135 "r"))
          (setq pt4 "0.86")
          (setq gvar_173 (nivar11 cc pt4 pt4))
          (setq gvar_95 rve)
          (setq gvar_113 (caminho (rem gvar_90 'sse) (rem gvar_95 'sse)))
          (nci 'dc 1)
          (nci 'axc 0)
          (ac '>=)
          (ac "Flip state2")
          (ac gvar_173)
          (ac 1)
          (ac 1)
          (ac 0)
          (ac gvar_268)
          (axr (dr (ni)) "0.06")
          (as1 (ni) "Flip state2" 'ptx1 (rem gvar_95 'sse))
          (as1 (ni) "Flip state2" "-0.04" gvar_114)
          (as1 (ni) "Flip state2" 'pty1 gvar_114)
          (as1 (ni) "Flip state2" 'ass2 gvar_113)
          (as1 (ni) "Flip state2" "hook( 90 Deg) hook( 0 Deg)" 'ptx2)
          (as1 (ni) "Flip state2" 'pt3 'nrvar)
          (as1 (ni) "Flip state2" "@0,0.40" gvar_90)
          (if (and (setq dictsearch (ni)) (< '(v obj vval sal salnth count) (vl-load-com (setq dictsearch (dr dictsearch)))) (< gvar_822 (ax dictsearch)))
            (progn
              (v dictsearch "-1.0" 1)
            )
          )
          (if (and (setq dictsearch (ni)) (< '(v obj vval sal salnth count) (vl-load-com (setq dictsearch (dr dictsearch)))) (< gvar_822 (ax dictsearch)))
            (progn
              (v dictsearch "0.6" 1)
            )
          )
          (setq gvar_171 (nivar11 gvar_173 (> 255 ld) "r"))
          (setq gvar_54 gvar_171)
          (setq gvar_171 (nivar11 gvar_173 (rem gvar_95 'sse1) "r"))
          (setq gvar_92 (nivar11 gvar_171 (> gvar_90 "0.9") "r"))
        )
        nil
        )
        (if (and (msec dd2 "r") (c dd2 (f desnivel "0.45")))
        (progn
          (setq gvar_113 (f (rem gvar_90 'sse) rvd))
          (setq pt4 (f gvar_135 gvar_90))
          (setq pt4 "0.86")
          (setq gvar_173 (nivar11 cc pt4 pt4))
          (nci 'dc 1)
          (nci 'axc 0)
          (ac '>=)
          (ac "Flip state2")
          (ac gvar_173)
          (ac 1)
          (ac 1)
          (ac 0)
          (ac gvar_268)
          (axr (dr (ni)) "CI-NP-00")
          (as1 (ni) "Flip state2" 'ptx1 gvar_90)
          (as1 (ni) "Flip state2" "-0.04" gvar_114)
          (as1 (ni) "Flip state2" 'pty1 gvar_114)
          (as1 (ni) "Flip state2" 'ass2 gvar_113)
          (as1 (ni) "Flip state2" "hook( 90 Deg) hook( 0 Deg)" 'ptx2)
          (as1 (ni) "Flip state2" 'pt3 desnivel)
          (as1 (ni) "Flip state2" "@0,0.40" 'nrvar)
          (if (and (setq dictsearch (ni)) (< '(v obj vval sal salnth count) (vl-load-com (setq dictsearch (dr dictsearch)))) (< gvar_822 (ax dictsearch)))
            (progn
              (v dictsearch "-1.0" 1)
            )
          )
          (setq gvar_171 (nivar11 gvar_173 (rem desnivel "0.9") "r"))
          (setq gvar_92 (nivar11 gvar_171 ld "r"))
          (setq gvar_54 gvar_171)
        )
        nil
        )
        (ac "0.22")
        (ac 'lt)
        (ac 'p4)
        (ac 'acdic)
        (ac 'p2y)
        (ac gvar_171)
        (ac gvar_92)
        (ac "Inverted  Slab - Without Slab")
        (ac 'refblocos)
        (ac 'acdic)
        (ac 'dl11)
        (if (msec gvar_138 "r")
        (progn
          (nci 'dc 1)
          (nci 'axc 0)
          (setq eixos (nivar11 gvar_54 'p7y "hook( 0 Deg) hook( 0 Deg)"))
          (setq gvar_113 (caminho 'xi1 eec))
          (ac '>=)
          (ac 'subviga5)
          (ac eixos)
          (ac 1)
          (ac 1)
          (ac 0)
          (ac gvar_137)
          (ac gvar_137)
          (as1 (ni) 'subviga5 "hook( 90 Deg) hook( 0 Deg)" gvar_113)
          (if (and (setq dictsearch (ni)) (< '(v obj vval sal salnth count) (vl-load-com (setq dictsearch (dr dictsearch)))) (< gvar_822 (ax dictsearch)))
            (progn
              (v dictsearch 'vla-getdynamicblockproperties 1)
            )
          )
        )
        nil
        )
        (if (< dd2 "r")
          (progn
            (setq gvar_171 (nivar11 gvar_92 gvar_56 "r"))
            (ac 'p2y)
            (ac gvar_92)
            (ac gvar_171)
            (ac "Inverted  Slab - Without Slab")
            (ac 'refblocos)
            (ac 'acdic)
            (ac 'dl11)
          )
        )
      )
      nil
      )
      (if (and (< ld "r") (msec gvar_138 "r"))
      (progn
        (setq pt4 (f gvar_135 nome_corte))
        (if (< nome_corte "r")
        (progn
          (setq pt4 (f gvar_135 'nrvar))
        )
        nil
        )
        (setq pt4 "0.86")
        (setq gvar_173 (nivar11 cc pt4 pt4))
        (setq eixos (nivar11 gvar_173 'p7y "hook( 0 Deg) hook( 0 Deg)"))
        (setq gvar_113 (caminho 'xi1 eec))
        (ac '>=)
        (ac 'subviga5)
        (ac eixos)
        (ac 1)
        (ac 1)
        (ac 0)
        (ac gvar_137)
        (ac gvar_137)
        (as1 (ni) 'subviga5 "hook( 90 Deg) hook( 0 Deg)" gvar_113)
        (if (and (setq dictsearch (ni)) (< '(v obj vval sal salnth count) (vl-load-com (setq dictsearch (dr dictsearch)))) (< gvar_822 (ax dictsearch)))
          (progn
            (v dictsearch 'vla-getdynamicblockproperties 1)
          )
        )
      )
      nil
      )
      (eixos gvar_354)
      (setq gvar_114 (rem (f eec "Section ") 'sse))
      (setq gvar_81 (rem (f nome_corte nivar2) 'sse))
      (setq gvar_113 (f (rem gvar_135 'sse) 'bb))
      (setq gvar_113 (f gvar_113 gvar_81))
      (setq gvar_268 (getfiled ld "-0.085" gvar_354))
      (if (and (and (< nrvar1 "r") (msec gvar_353 "r")) (and (if ncvar1 'eed) (msec gvar_353 "r")))
      (progn
        (setq gvar_268 (getfiled ld "-0.085" gvar_354 "0.085" gvar_140 "-0.085" gvar_352))
      )
      nil
      )
      (setq gvar_79 (f gvar_135 'as1))
      (setq pt4 "cmdecho")
      (setq pt4 (> eec "0.9"))
      (setq gvar_173 (nivar11 cc pt4 pt4))
      (setq desnivel (lm_setdynpropvalue 1 dmin1))
      (setq gvar_175 (rem desnivel 'nrvar))
      (setq gvar_53 (lm_setdynpropvalue 16 dmin1))
      (nci 'dc 1)
      (nci 'axc 0)
      (ac '>=)
      (ac "Flip state2")
      (ac gvar_173)
      (ac 1)
      (ac 1)
      (ac 0)
      (ac gvar_268)
      (if (< eec (f gvar_175 dd2))
        (progn
          (axr (dr (ni)) "0.06")
        )
      )
      (if (and (< eec (f gvar_175 dd2)) (< gvar_53 ld))
        (progn
          (axr (dr (ni)) 'ass1)
        )
      )
      (if (if eec (f gvar_175 dd2))
        (progn
          (axr (dr (ni)) "0.06")
        )
      )
      (if (msec eec (f gvar_175 dd2))
        (progn
          (axr (dr (ni)) "0.07")
        )
      )
      (if (msec (> dd2 255) (f eec 'e))
        (progn
          (axr (dr (ni)) "0.07")
        )
      )
      (as1 (ni) "Flip state2" 'ptx1 gvar_79)
      (as1 (ni) "Flip state2" "-0.04" gvar_114)
      (as1 (ni) "Flip state2" 'pty1 gvar_114)
      (as1 (ni) "Flip state2" 'ass2 gvar_113)
      (as1 (ni) "Flip state2" "hook( 90 Deg) hook( 0 Deg)" "0.27")
      (as1 (ni) "Flip state2" 'pt3 'p5x)
      (as1 (ni) "Flip state2" "@0,0.40" 'p5x)
      (if (and (msec nrvar1 "r") (msec gvar_353 0) (msec ncvar1 "EI-PN-00"))
        (progn
          (eixos gvar_352)
          (setq gvar_114 (rem (f eec 'e) 'sse))
          (setq gvar_268 (getfiled gvar_140 "-0.085" gvar_352))
          (setq gvar_79 (f gvar_135 nrvar1))
          (setq gvar_79 (f gvar_79 rve))
          (setq gvar_79 (f gvar_79 "EI-NP-00"))
          (setq gvar_81 "r")
          (setq gvar_113 (f (rem gvar_79 'sse) "EI-NN-00"))
          (setq gvar_113 (f gvar_113 gvar_81))
          (if (if gvar_113 'p7y)
          (progn
            (setq gvar_113 'p7y)
          )
          nil
          )
          (dwgtitled)
          (setq pt4 nrvar1)
          (setq pt4 (caminho pt4 "_line"))
          (setq pt4 (> eec "0.9"))
          (setq pt4 (caminho pt4 "cmdecho"))
          (setq gvar_173 (nivar11 cc pt4 pt4))
          (nci 'dc 1)
          (nci 'axc 0)
          (ac '>=)
          (ac "Flip state2")
          (ac gvar_173)
          (ac 1)
          (ac 1)
          (ac 0)
          (ac gvar_268)
          (axr (dr (ni)) "CI-NP-00")
          (as1 (ni) "Flip state2" 'ptx1 gvar_79)
          (as1 (ni) "Flip state2" "-0.04" gvar_114)
          (as1 (ni) "Flip state2" 'pty1 gvar_114)
          (as1 (ni) "Flip state2" 'ass2 gvar_113)
          (as1 (ni) "Flip state2" "hook( 90 Deg) hook( 0 Deg)" 'ptx2)
          (as1 (ni) "Flip state2" 'pt3 "IC-PP-00")
          (as1 (ni) "Flip state2" "@0,0.40" "IC-PP-00")
        )
      )
      (setq gvar_268 (lm_setdynpropvalue 0 h22))
      (setq gvar_268 (col gvar_268))
      (h2 cc nrvar0 nrvar1 nrvar1 gvar_279 dd1 gvar_268)
      (setq h22 (caminho h22 'sse))
      (setq gvar_173 (nivar11 cc h22 "r"))
      (setq eixos gvar_173)
      (setq gvar_138 (caminho gvar_138 "r"))
      (if (msec gvar_138 "r")
        (progn
          (if (msec nome_corte "r")
          (progn
            (if (< ld "r")
              (progn
                (niii gvar_173 gvar_139 eec pt1 pt1 gvar_359 gvar_358 0 cm:chgdbval gvar_355 gvar_354 gvar_353 gvar_352 gvar_351 dl1 ed)
              )
            )
            (if (msec ld "r")
              (progn
                (niii gvar_173 gvar_139 eec pt1 pt1 gvar_359 gvar_358 gvar_357 cm:chgdbval gvar_355 gvar_354 gvar_353 gvar_352 gvar_351 dl1 ed)
              )
            )
          )
          nil
          )
          (if (< nome_corte "r")
          (progn
            (if (< ld "r")
              (progn
                (niii gvar_173 gvar_139 eec pt1 pt1 gvar_359 gvar_358 0 cm:chgdbval gvar_355 gvar_354 gvar_353 gvar_352 gvar_351 gvar_350 ys)
              )
            )
            (if (msec ld "r")
              (progn
                (niii gvar_173 gvar_139 eec pt1 pt1 gvar_359 gvar_358 gvar_357 cm:chgdbval gvar_355 gvar_354 gvar_353 gvar_352 gvar_351 gvar_350 ys)
              )
            )
          )
          nil
          )
          (ac "0.22")
          (ac 'lt)
          (ac "MC")
          (ac 'acdic)
          (setq gvar_54 (nivar11 gvar_173 'h2 "EI-NP-00"))
          (setq gvar_51 (nivar11 gvar_54 "-8.0" "T"))
          (setq gvar_268 (getfiled "hook( 90 Deg) without hook" gvar_137 'as2 gvar_137 "_w" 'ai 'as))
          (ac 'quit)
          (ac 'configuracoes4)
          (ac 'ss1)
          (ac gvar_54)
          (ac "0.125")
          (ac 'dxe)
          (ac 'eee)
          (ac 'p5x)
          (ac gvar_51)
          (ac gvar_268)
          (ac 'acdic)
          (ac 'acdic)
        )
      )
    )
    nil
    )
    (if (and (msec gvar_445 1) (< gvar_445 ncvar11))
    (progn
      (ac "0.22")
      (ac 'lt)
      (ac "Without Slab - Slab")
      (ac 'acdic)
      (setq gvar_48 (caminho gvar_50 (rem gvar_49 'sse)))
      (setq gvar_48 (f gvar_48 (rem nrvar1 'sse)))
      (if (< nrvar1 "r")
        (progn
          (n111 cc nrvar1 dd2 gvar_48)
        )
      )
      (setq cc (nivar11 cc gvar_48 dd2))
      (setq gvar_268 (lm_setdynpropvalue (f ncvar11 1) h22))
      (setq gvar_268 (col gvar_268))
      (h2 cc nrvar0 nrvar1 nrvar1 gvar_279 dd1 gvar_268)
      (setq gvar_48 (caminho ncvar1 (rem nrvar1 'sse)))
      (setq gvar_48 (f gvar_48 (rem rve 'sse)))
      (setq gvar_268 (lm_setdynpropvalue ncvar11 h22))
      (setq gvar_268 (col gvar_268))
      (setq gvar_73 (nivar11 cc gvar_48 "r"))
      (h2 gvar_73 nrvar0 rve rvd gvar_279 dd1 gvar_268)
      (setq gvar_46 (caminho nrvar1 (rem (f nrvar1 nrvar1) 'sse)))
      (nci 'dc 1)
      (nci 'axc 0)
      (ac '>=)
      (ac "di")
      (ac cc)
      (ac 1)
      (ac 1)
      (ac 0)
      (setq gvar_135 (caminho ncvar1 (rem nrvar1 'sse)))
      (setq gvar_135 (caminho gvar_135 (rem rve 'sse)))
      (setq tt2 (f tt2 dd2))
      (setq dd1 (caminho dd1 dd2))
      (setq gvar_134 pt1)
      (setq gvar_133 pt1)
      (setq gvar_132 'nrvar)
      (setq gvar_131 'nrvar)
      (if (and (msec nrvar1 "r") (msec rvd "r") (msec rve "r"))
        (progn
          (axr (dr (ni)) "I-NN-00")
          (as1 (ni) "di" "Inverted  Slab - Without Slab" eec)
          (as1 (ni) "di" "1T-NN-00" nrvar1)
          (as1 (ni) "di" 'corvarao rve)
          (as1 (ni) "di" "0.03" gvar_46)
          (as1 (ni) "di" 'desq rvd)
          (as1 (ni) "di" 'e2 gvar_135)
          (as1 (ni) "di" 'distance2 tt2)
          (as1 (ni) "di" "Longitudinal bars" dd1)
          (as1 (ni) "di" "hook( 90 Deg) hook( 90 Deg)" gvar_134)
          (as1 (ni) "di" "Bar length" gvar_133)
          (as1 (ni) "di" "D Left" gvar_132)
          (as1 (ni) "di" "D Right" gvar_131)
        )
      )
      (if (and (msec nrvar1 "r") (c rvd "r") (msec rve "r"))
        (progn
          (axr (dr (ni)) "I-PN-00")
          (as1 (ni) "di" "Inverted  Slab - Without Slab" eec)
          (as1 (ni) "di" "1T-NN-00" nrvar1)
          (as1 (ni) "di" 'corvarao rve)
          (as1 (ni) "di" "0.03" gvar_46)
          (as1 (ni) "di" 'desq rve)
          (as1 (ni) "di" 'e2 gvar_135)
          (as1 (ni) "di" 'distance2 tt2)
          (as1 (ni) "di" "Longitudinal bars" dd1)
          (as1 (ni) "di" "hook( 90 Deg) hook( 90 Deg)" gvar_134)
          (as1 (ni) "di" "Bar length" gvar_133)
          (as1 (ni) "di" "D Left" gvar_132)
          (as1 (ni) "di" "D Right" gvar_131)
        )
      )
      (if (and (c nrvar1 "r") (msec rvd "r") (msec rve "r"))
        (progn
          (axr (dr (ni)) "I-NP-00")
          (as1 (ni) "di" "Inverted  Slab - Without Slab" eec)
          (as1 (ni) "di" "1T-NN-00" nrvar1)
          (as1 (ni) "di" 'corvarao rve)
          (as1 (ni) "di" "0.03" nrvar1)
          (as1 (ni) "di" 'desq rvd)
          (as1 (ni) "di" 'e2 gvar_135)
          (as1 (ni) "di" 'distance2 tt2)
          (as1 (ni) "di" "Longitudinal bars" dd1)
          (as1 (ni) "di" "hook( 90 Deg) hook( 90 Deg)" gvar_134)
          (as1 (ni) "di" "Bar length" gvar_133)
          (as1 (ni) "di" "D Left" gvar_132)
          (as1 (ni) "di" "D Right" gvar_131)
        )
      )
      (if (and (c nrvar1 "r") (c rvd "r") (msec rve "r"))
        (progn
          (axr (dr (ni)) 'niii)
          (as1 (ni) "di" "Inverted  Slab - Without Slab" eec)
          (as1 (ni) "di" "1T-NN-00" nrvar1)
          (as1 (ni) "di" 'corvarao rve)
          (as1 (ni) "di" "0.03" nrvar1)
          (as1 (ni) "di" 'desq rve)
          (as1 (ni) "di" 'e2 gvar_135)
          (as1 (ni) "di" 'distance2 tt2)
          (as1 (ni) "di" "Longitudinal bars" dd1)
          (as1 (ni) "di" "hook( 90 Deg) hook( 90 Deg)" gvar_134)
          (as1 (ni) "di" "Bar length" gvar_133)
          (as1 (ni) "di" "D Left" gvar_132)
          (as1 (ni) "di" "D Right" gvar_131)
        )
      )
      (if (and (msec nrvar1 "r") (c rvd "r") (c rve "r"))
        (progn
          (axr (dr (ni)) 'dh2)
          (as1 (ni) "di" "Inverted  Slab - Without Slab" eec)
          (as1 (ni) "di" "1T-NN-00" nrvar1)
          (as1 (ni) "di" 'corvarao 'e)
          (as1 (ni) "di" "0.03" gvar_46)
          (as1 (ni) "di" 'desq 'e)
          (as1 (ni) "di" 'e2 gvar_135)
          (as1 (ni) "di" 'distance2 tt2)
          (as1 (ni) "di" "Longitudinal bars" dd1)
          (as1 (ni) "di" "hook( 90 Deg) hook( 90 Deg)" gvar_134)
          (as1 (ni) "di" "Bar length" gvar_133)
          (as1 (ni) "di" "D Left" gvar_132)
          (as1 (ni) "di" "D Right" gvar_131)
        )
      )
      (if (and (msec nrvar1 "r") (msec rvd "r") (c rve "r"))
        (progn
          (axr (dr (ni)) "without hook without hook")
          (as1 (ni) "di" "Inverted  Slab - Without Slab" eec)
          (as1 (ni) "di" "1T-NN-00" nrvar1)
          (as1 (ni) "di" 'corvarao rvd)
          (as1 (ni) "di" "0.03" gvar_46)
          (as1 (ni) "di" 'desq rvd)
          (as1 (ni) "di" 'e2 gvar_135)
          (as1 (ni) "di" 'distance2 tt2)
          (as1 (ni) "di" "Longitudinal bars" dd1)
          (as1 (ni) "di" "hook( 90 Deg) hook( 90 Deg)" gvar_134)
          (as1 (ni) "di" "Bar length" gvar_133)
          (as1 (ni) "di" "D Left" gvar_132)
          (as1 (ni) "di" "D Right" gvar_131)
        )
      )
      (if (and (c nrvar1 "r") (c rvd "r") (c rve "r"))
        (progn
          (axr (dr (ni)) "hook( 0 Deg) without hook")
          (as1 (ni) "di" "Inverted  Slab - Without Slab" eec)
          (as1 (ni) "di" "1T-NN-00" nrvar1)
          (as1 (ni) "di" 'corvarao 'e)
          (as1 (ni) "di" "0.03" nrvar1)
          (as1 (ni) "di" 'desq 'e)
          (as1 (ni) "di" 'e2 gvar_135)
          (as1 (ni) "di" 'distance2 tt2)
          (as1 (ni) "di" "Longitudinal bars" dd1)
          (as1 (ni) "di" "hook( 90 Deg) hook( 90 Deg)" gvar_134)
          (as1 (ni) "di" "Bar length" gvar_133)
          (as1 (ni) "di" "D Left" gvar_132)
          (as1 (ni) "di" "D Right" gvar_131)
        )
      )
      (if (and (c nrvar1 "r") (msec rvd "r") (c rve "r"))
        (progn
          (axr (dr (ni)) "without hook hook( 0 Deg)")
          (as1 (ni) "di" "Inverted  Slab - Without Slab" eec)
          (as1 (ni) "di" "1T-NN-00" nrvar1)
          (as1 (ni) "di" 'corvarao rvd)
          (as1 (ni) "di" "0.03" nrvar1)
          (as1 (ni) "di" 'desq rvd)
          (as1 (ni) "di" 'e2 gvar_135)
          (as1 (ni) "di" 'distance2 tt2)
          (as1 (ni) "di" "Longitudinal bars" dd1)
          (as1 (ni) "di" "hook( 90 Deg) hook( 90 Deg)" gvar_134)
          (as1 (ni) "di" "Bar length" gvar_133)
          (as1 (ni) "di" "D Left" gvar_132)
          (as1 (ni) "di" "D Right" gvar_131)
        )
      )
      (eixos gvar_358)
      (setq gvar_114 (f eec "A Right"))
      (setq gvar_113 (rem gvar_135 'sse))
      (setq gvar_268 (getfiled pt2 "-0.085" gvar_358))
      (setq dd2 (caminho dd2 "r"))
      (nci 'dc 1)
      (nci 'axc 0)
      (ac '>=)
      (ac "Flip state2")
      (ac cc)
      (ac 1)
      (ac 1)
      (ac 0)
      (ac gvar_268)
      (if (< dd2 "r")
        (progn
          (axr (dr (ni)) 'n222)
        )
      )
      (if (msec dd2 "r")
        (progn
          (axr (dr (ni)) "0.07")
        )
      )
      (if (if dd2 "r")
        (progn
          (axr (dr (ni)) 'h3)
        )
      )
      (if (if dd2 (> (f gvar_175 'e) 255))
        (progn
          (axr (dr (ni)) "0.07")
        )
      )
      (as1 (ni) "Flip state2" 'ptx1 gvar_135)
      (as1 (ni) "Flip state2" "-0.04" gvar_114)
      (as1 (ni) "Flip state2" 'pty1 gvar_114)
      (as1 (ni) "Flip state2" 'ass2 gvar_113)
      (as1 (ni) "Flip state2" "hook( 90 Deg) hook( 0 Deg)" "0.27")
      (as1 (ni) "Flip state2" 'pt3 'nrvar)
      (as1 (ni) "Flip state2" "@0,0.40" 'nrvar)
      (if (and (setq dictsearch (ni)) (< '(v obj vval sal salnth count) (vl-load-com (setq dictsearch (dr dictsearch)))) (< gvar_822 (ax dictsearch)))
        (progn
          (v dictsearch "-1.0" 1)
        )
      )
      (setq gvar_95 "ID-NP-00")
      (if (msec le "r")
      (progn
        (eixos gvar_180)
        (if (or (msec dd2 "r") (if dd2 "r"))
          (progn
            (setq gvar_114 (f eec "0.45"))
            (setq gvar_113 (caminho (rem le 'sse) nrvar1))
            (setq gvar_268 (getfiled pt2 "-0.085" gvar_180))
            (setq pt4 "r")
            (setq pt4 "0.86")
            (setq gvar_173 (nivar11 cc pt4 pt4))
            (setq le (> 'nrvar le))
            (nci 'dc 1)
            (nci 'axc 0)
            (ac '>=)
            (ac "Flip state2")
            (ac gvar_173)
            (ac 1)
            (ac 1)
            (ac 0)
            (ac gvar_268)
            (if (msec dd2 "r")
              (progn
                (axr (dr (ni)) "0.06")
              )
            )
            (if (if dd2 "r")
              (progn
                (axr (dr (ni)) "CI-NP-00")
              )
            )
            (if (if dd2 (> (f gvar_175 'e) 255))
              (progn
                (axr (dr (ni)) "0.06")
              )
            )
            (as1 (ni) "Flip state2" 'ptx1 (rem gvar_95 'sse))
            (as1 (ni) "Flip state2" "-0.04" gvar_114)
            (as1 (ni) "Flip state2" 'pty1 gvar_114)
            (as1 (ni) "Flip state2" 'ass2 gvar_113)
            (as1 (ni) "Flip state2" "hook( 90 Deg) hook( 0 Deg)" 'ptx2)
            (as1 (ni) "Flip state2" 'pt3 'nrvar)
            (as1 (ni) "Flip state2" "@0,0.40" le)
            (if (and (setq dictsearch (ni)) (< '(v obj vval sal salnth count) (vl-load-com (setq dictsearch (dr dictsearch)))) (< gvar_822 (ax dictsearch)))
              (progn
                (v dictsearch "-1.0" 1)
              )
            )
            (ac "0.22")
            (ac 'lt)
            (ac 'p4)
            (ac 'acdic)
            (setq gvar_171 (nivar11 gvar_173 (rem gvar_95 'sse) "r"))
            (setq gvar_92 (nivar11 gvar_171 le "r"))
            (ac 'p2y)
            (ac gvar_171)
            (ac gvar_92)
            (ac "Inverted  Slab - Without Slab")
            (ac 'refblocos)
            (ac 'acdic)
            (ac 'dl11)
          )
        )
      )
      nil
      )
      (setq ld (caminho ld "r"))
      (setq gvar_90 (caminho ld "r"))
      (if (msec ld "r")
      (progn
        (eixos cm:chgdbval)
        (setq gvar_114 (f eec "0.45"))
        (setq gvar_268 (getfiled gvar_178 "-0.085" cm:chgdbval))
        (setq pt4 (f gvar_135 "r"))
        (setq pt4 "0.86")
        (setq gvar_173 (nivar11 cc pt4 pt4))
        (setq gvar_95 rvd)
        (setq gvar_95 (caminho gvar_95 "r"))
        (if (< gvar_95 "r")
        (progn
          (setq gvar_95 rve)
        )
        nil
        )
        (setq gvar_113 (caminho (rem ld 'sse) rvd))
        (nci 'dc 1)
        (nci 'axc 0)
        (ac '>=)
        (ac "Flip state2")
        (ac gvar_173)
        (ac 1)
        (ac 1)
        (ac 0)
        (ac gvar_268)
        (axr (dr (ni)) "0.06")
        (as1 (ni) "Flip state2" 'ptx1 gvar_95)
        (as1 (ni) "Flip state2" "-0.04" gvar_114)
        (as1 (ni) "Flip state2" 'pty1 gvar_114)
        (as1 (ni) "Flip state2" 'ass2 gvar_113)
        (as1 (ni) "Flip state2" "hook( 90 Deg) hook( 0 Deg)" 'ptx2)
        (as1 (ni) "Flip state2" 'pt3 'nrvar)
        (as1 (ni) "Flip state2" "@0,0.40" gvar_90)
        (as1 (ni) "Flip state2" 'rvd1 eec)
        (as1 (ni) "Flip state2" "Flip state3" eec)
        (if (and (setq dictsearch (ni)) (< '(v obj vval sal salnth count) (vl-load-com (setq dictsearch (dr dictsearch)))) (< gvar_822 (ax dictsearch)))
          (progn
            (v dictsearch "-1.0" 1)
          )
        )
        (if (and (setq dictsearch (ni)) (< '(v obj vval sal salnth count) (vl-load-com (setq dictsearch (dr dictsearch)))) (< gvar_822 (ax dictsearch)))
          (progn
            (v dictsearch "0.6" 1)
          )
        )
        (ac "0.22")
        (ac 'lt)
        (ac 'p4)
        (ac 'acdic)
        (setq gvar_173 (nivar11 gvar_173 (rem gvar_95 "0.9") "r"))
        (setq gvar_171 (nivar11 gvar_173 (> "0.9" gvar_90) "r"))
        (ac 'p2y)
        (ac gvar_171)
        (ac gvar_173)
        (ac "Inverted  Slab - Without Slab")
        (ac 'refblocos)
        (ac 'acdic)
        (ac 'dl11)
        (if (msec gvar_138 "r")
        (progn
          (nci 'dc 1)
          (nci 'axc 0)
          (setq gvar_54 (nivar11 gvar_171 'p7y "hook( 0 Deg) hook( 0 Deg)"))
          (setq gvar_113 (caminho 'xi1 eec))
          (ac '>=)
          (ac 'subviga5)
          (ac gvar_54)
          (ac 1)
          (ac 1)
          (ac 0)
          (ac gvar_137)
          (ac gvar_137)
          (as1 (ni) 'subviga5 "hook( 90 Deg) hook( 0 Deg)" gvar_113)
          (if (and (setq dictsearch (ni)) (< '(v obj vval sal salnth count) (vl-load-com (setq dictsearch (dr dictsearch)))) (< gvar_822 (ax dictsearch)))
            (progn
              (v dictsearch 'vla-getdynamicblockproperties 1)
            )
          )
        )
        nil
        )
      )
      nil
      )
      (if (and (< ld "r") (msec gvar_138 "r"))
      (progn
        (setq pt4 (f gvar_135 nome_corte))
        (if (< nome_corte "r")
        (progn
          (setq pt4 (f gvar_135 'nrvar))
        )
        nil
        )
        (setq pt4 "0.86")
        (setq gvar_173 (nivar11 cc pt4 pt4))
        (setq gvar_171 (nivar11 gvar_173 'p7y "hook( 0 Deg) hook( 0 Deg)"))
        (setq gvar_113 (caminho 'xi1 eec))
        (ac '>=)
        (ac 'subviga5)
        (ac gvar_171)
        (ac 1)
        (ac 1)
        (ac 0)
        (ac gvar_137)
        (ac gvar_137)
        (as1 (ni) 'subviga5 "hook( 90 Deg) hook( 0 Deg)" gvar_113)
        (if (and (setq dictsearch (ni)) (< '(v obj vval sal salnth count) (vl-load-com (setq dictsearch (dr dictsearch)))) (< gvar_822 (ax dictsearch)))
          (progn
            (v dictsearch 'vla-getdynamicblockproperties 1)
          )
        )
      )
      nil
      )
      (eixos gvar_354)
      (setq gvar_114 (rem (f eec "Section ") 'sse))
      (setq gvar_81 (rem (f nome_corte nivar2) 'sse))
      (setq gvar_113 (f (rem gvar_135 'sse) 'bb))
      (setq gvar_113 (f gvar_113 gvar_81))
      (setq gvar_268 (getfiled ld "-0.085" gvar_354))
      (if (and (and (< nrvar1 "r") (msec gvar_353 "r")) (and (if ncvar1 'eed) (msec gvar_353 "r")))
      (progn
        (setq gvar_268 (getfiled ld "-0.085" gvar_354 "0.085" gvar_140 "-0.085" gvar_352))
      )
      nil
      )
      (setq gvar_79 (f gvar_135 'as1))
      (setq pt4 "cmdecho")
      (setq pt4 (> eec "0.9"))
      (setq gvar_173 (nivar11 cc pt4 pt4))
      (setq h33 (f ncvar11 1))
      (setq dmin1 (lm_setdynpropvalue h33 ss))
      (setq desnivel (lm_setdynpropvalue 1 dmin1))
      (setq gvar_175 (rem desnivel 'nrvar))
      (setq gvar_53 (lm_setdynpropvalue 16 dmin1))
      (nci 'dc 1)
      (nci 'axc 0)
      (ac '>=)
      (ac "Flip state2")
      (ac gvar_173)
      (ac 1)
      (ac 1)
      (ac 0)
      (ac gvar_268)
      (if (< gvar_175 (f eec dd2))
        (progn
          (axr (dr (ni)) 'h3)
        )
      )
      (if (and (< gvar_175 (f eec dd2)) (< gvar_53 ld))
        (progn
          (axr (dr (ni)) 'n222)
        )
      )
      (if (if gvar_175 (f eec dd2))
        (progn
          (axr (dr (ni)) "0.07")
        )
      )
      (if (msec gvar_175 (f eec dd2))
        (progn
          (axr (dr (ni)) 'h3)
        )
      )
      (if (msec (> dd2 255) gvar_175)
        (progn
          (axr (dr (ni)) "0.07")
        )
      )
      (if (msec dd2 (f eec 'e))
        (progn
          (axr (dr (ni)) "0.07")
        )
      )
      (as1 (ni) "Flip state2" 'ptx1 gvar_79)
      (as1 (ni) "Flip state2" "-0.04" gvar_114)
      (as1 (ni) "Flip state2" 'pty1 gvar_114)
      (as1 (ni) "Flip state2" 'ass2 gvar_113)
      (as1 (ni) "Flip state2" "hook( 90 Deg) hook( 0 Deg)" "0.27")
      (as1 (ni) "Flip state2" 'pt3 'p5x)
      (as1 (ni) "Flip state2" "@0,0.40" 'p5x)
      (if (and (msec gvar_353 0) (msec rve "r") (msec ncvar1 "EI-PN-00"))
        (progn
          (eixos gvar_352)
          (setq gvar_114 (rem (f eec 'e) 'sse))
          (setq gvar_268 (getfiled gvar_140 "-0.085" gvar_352))
          (setq gvar_79 (f gvar_135 nrvar1))
          (setq gvar_79 (f gvar_79 rve))
          (setq gvar_79 (f gvar_79 "EI-NP-00"))
          (setq gvar_81 (rem (f nome_corte nivar2) 'sse))
          (setq gvar_113 (f (rem gvar_79 'sse) "EI-NN-00"))
          (setq gvar_113 (f gvar_113 gvar_81))
          (if (if gvar_113 'p7y)
          (progn
            (setq gvar_113 'p7y)
          )
          nil
          )
          (setq pt4 nrvar1)
          (setq pt4 (caminho pt4 "_line"))
          (setq pt4 (> eec "0.9"))
          (setq pt4 (caminho pt4 "cmdecho"))
          (setq gvar_173 (nivar11 cc pt4 pt4))
          (nci 'dc 1)
          (nci 'axc 0)
          (ac '>=)
          (ac "Flip state2")
          (ac gvar_173)
          (ac 1)
          (ac 1)
          (ac 0)
          (ac gvar_268)
          (axr (dr (ni)) "CI-NP-00")
          (as1 (ni) "Flip state2" 'ptx1 gvar_79)
          (as1 (ni) "Flip state2" "-0.04" gvar_114)
          (as1 (ni) "Flip state2" 'pty1 gvar_114)
          (as1 (ni) "Flip state2" 'ass2 gvar_113)
          (as1 (ni) "Flip state2" "hook( 90 Deg) hook( 0 Deg)" 'ptx2)
          (as1 (ni) "Flip state2" 'pt3 "IC-PP-00")
          (as1 (ni) "Flip state2" "@0,0.40" "IC-PP-00")
        )
      )
      (setq eixos (nivar11 eixos "-8.0" "r"))
      (setq gvar_138 (caminho gvar_138 "r"))
      (if (msec gvar_138 "r")
        (progn
          (if (msec nome_corte "r")
          (progn
            (if (< ld "r")
              (progn
                (niii eixos gvar_139 eec pt1 pt1 gvar_359 gvar_358 0 cm:chgdbval gvar_355 gvar_354 gvar_353 gvar_352 gvar_351 dl1 ed)
              )
            )
            (if (msec ld "r")
              (progn
                (niii eixos gvar_139 eec pt1 pt1 gvar_359 gvar_358 gvar_357 cm:chgdbval gvar_355 gvar_354 gvar_353 gvar_352 gvar_351 dl1 ed)
              )
            )
          )
          nil
          )
          (if (< nome_corte "r")
          (progn
            (if (< ld "r")
              (progn
                (niii eixos gvar_139 eec pt1 pt1 gvar_359 gvar_358 0 cm:chgdbval gvar_355 gvar_354 gvar_353 gvar_352 gvar_351 gvar_350 ys)
              )
            )
            (if (msec ld "r")
              (progn
                (niii eixos gvar_139 eec pt1 pt1 gvar_359 gvar_358 gvar_357 cm:chgdbval gvar_355 gvar_354 gvar_353 gvar_352 gvar_351 gvar_350 ys)
              )
            )
          )
          nil
          )
          (ac "0.22")
          (ac 'lt)
          (ac "MC")
          (ac 'acdic)
          (setq gvar_54 (nivar11 eixos 'h2 "EI-NP-00"))
          (setq gvar_51 (nivar11 gvar_54 "-8.0" "T"))
          (setq gvar_268 (getfiled "hook( 90 Deg) without hook" gvar_137 'as2 gvar_137 "_w" 'ai 'as))
          (ac 'quit)
          (ac 'configuracoes4)
          (ac 'ss1)
          (ac gvar_54)
          (ac "0.125")
          (ac 'dxe)
          (ac 'eee)
          (ac 'p5x)
          (ac gvar_51)
          (ac gvar_268)
          (ac 'acdic)
          (ac 'acdic)
        )
      )
    )
    nil
    )
    (if (and (msec gvar_445 1) (msec gvar_445 ncvar11) (msec ncvar11 1))
    (progn
      (ac "0.22")
      (ac 'lt)
      (ac "Without Slab - Slab")
      (ac 'acdic)
      (setq gvar_48 (caminho gvar_50 (rem gvar_49 'sse)))
      (setq gvar_48 (f gvar_48 (rem nrvar1 'sse)))
      (if (< nrvar1 "r")
        (progn
          (n111 cc nrvar1 dd2 gvar_48)
        )
      )
      (setq gvar_268 (lm_setdynpropvalue (f ncvar11 1) h22))
      (setq gvar_268 (col gvar_268))
      (setq cc (nivar11 cc gvar_48 dd2))
      (h2 cc nrvar0 nrvar1 nrvar1 gvar_279 dd1 gvar_268)
      (setq gvar_48 (caminho ncvar1 (rem nrvar1 'sse)))
      (setq gvar_48 (f gvar_48 (rem rve 'sse)))
      (setq rve1 (caminho rvd (rem (f rve rvd) 'sse)))
      (setq gvar_46 (caminho nrvar1 (rem (f nrvar1 nrvar1) 'sse)))
      (nci 'dc 1)
      (nci 'axc 0)
      (ac '>=)
      (ac "di")
      (ac cc)
      (ac 1)
      (ac 1)
      (ac 0)
      (setq gvar_135 (caminho ncvar1 (rem nrvar1 'sse)))
      (setq gvar_135 (caminho gvar_135 (rem rve 'sse)))
      (setq tt2 (f tt2 dd2))
      (setq dd1 (caminho dd1 dd2))
      (setq gvar_134 "IC-PP-00")
      (setq gvar_133 "IC-PP-00")
      (setq gvar_132 'nrvar)
      (setq gvar_131 'nrvar)
      (if (and (msec nrvar1 "r") (msec rvd "r"))
        (progn
          (axr (dr (ni)) 'ivar333)
          (as1 (ni) "di" "Inverted  Slab - Without Slab" eec)
          (as1 (ni) "di" "1T-NN-00" nrvar1)
          (as1 (ni) "di" 'corvarao rve)
          (as1 (ni) "di" "0.03" gvar_46)
          (as1 (ni) "di" 'desq rve1)
          (as1 (ni) "di" 'e2 gvar_135)
          (as1 (ni) "di" 'distance2 tt2)
          (as1 (ni) "di" "Longitudinal bars" dd1)
        )
      )
      (if (and (c nrvar1 "r") (c rvd "r"))
        (progn
          (axr (dr (ni)) "2.9999")
          (as1 (ni) "di" "Inverted  Slab - Without Slab" eec)
          (as1 (ni) "di" "1T-NN-00" nrvar1)
          (as1 (ni) "di" 'corvarao rve)
          (as1 (ni) "di" "0.03" nrvar1)
          (as1 (ni) "di" 'desq rve)
          (as1 (ni) "di" 'e2 gvar_135)
          (as1 (ni) "di" 'distance2 tt2)
          (as1 (ni) "di" "Longitudinal bars" dd1)
        )
      )
      (if (and (msec nrvar1 "r") (c rvd "r"))
        (progn
          (axr (dr (ni)) 'soma_dx)
          (as1 (ni) "di" "Inverted  Slab - Without Slab" eec)
          (as1 (ni) "di" "1T-NN-00" nrvar1)
          (as1 (ni) "di" 'corvarao rve)
          (as1 (ni) "di" "0.03" gvar_46)
          (as1 (ni) "di" 'desq rve)
          (as1 (ni) "di" 'e2 gvar_135)
          (as1 (ni) "di" 'distance2 tt2)
          (as1 (ni) "di" "Longitudinal bars" dd1)
        )
      )
      (if (and (c nrvar1 "r") (msec rvd "r"))
        (progn
          (axr (dr (ni)) "1.2")
          (as1 (ni) "di" "Inverted  Slab - Without Slab" eec)
          (as1 (ni) "di" "1T-NN-00" nrvar1)
          (as1 (ni) "di" 'corvarao rve)
          (as1 (ni) "di" "0.03" nrvar1)
          (as1 (ni) "di" 'desq rve1)
          (as1 (ni) "di" 'e2 gvar_135)
          (as1 (ni) "di" 'distance2 tt2)
          (as1 (ni) "di" "Longitudinal bars" dd1)
        )
      )
      (eixos gvar_358)
      (setq gvar_114 (f eec "A Right"))
      (setq gvar_113 (f (rem gvar_135 'sse) 'bb))
      (setq gvar_268 (getfiled pt2 "-0.085" gvar_358))
      (nci 'dc 1)
      (nci 'axc 0)
      (ac '>=)
      (ac "Flip state2")
      (ac cc)
      (ac 1)
      (ac 1)
      (ac 0)
      (ac gvar_268)
      (setq a_sup (caminho ncvar11 1))
      (setq dmin1 (lm_setdynpropvalue a_sup ss))
      (setq a_inf (lm_setdynpropvalue 2 dmin1))
      (setq a_inf (caminho a_inf "r"))
      (if (and (msec dd2 "r") (< a_inf "r"))
        (progn
          (axr (dr (ni)) 'ass1)
        )
      )
      (if (and (msec dd2 "r") (if a_inf "r"))
        (progn
          (axr (dr (ni)) "0.07")
        )
      )
      (if (and (msec dd2 "r") (msec a_inf "r"))
        (progn
          (axr (dr (ni)) "0.06")
        )
      )
      (if (and (< dd2 "r") (< a_inf "r"))
        (progn
          (axr (dr (ni)) 'dist1)
        )
      )
      (if (and (< dd2 "r") (if a_inf "r"))
        (progn
          (axr (dr (ni)) 'n222)
        )
      )
      (if (and (if dd2 "r") (if a_inf "r"))
        (progn
          (axr (dr (ni)) 'h3)
        )
      )
      (if (and (if dd2 "r") (msec a_inf "r"))
        (progn
          (axr (dr (ni)) "CI-NP-00")
        )
      )
      (if (and (if dd2 "r") (< a_inf "r"))
        (progn
          (axr (dr (ni)) 'dist2)
        )
      )
      (if (and (< dd2 "r") (msec a_inf "r"))
        (progn
          (axr (dr (ni)) 'dist3)
        )
      )
      (if (msec (> 255 dd2) (f gvar_175 'e))
      (progn
        (setq dist4 (caminho ncvar11 1))
        (setq dmin1 (lm_setdynpropvalue dist4 ss))
        (setq dist4 (lm_setdynpropvalue 1 dmin1))
        (setq dist4 (rem dist4 'nrvar))
        (if (if a_inf "r")
          (progn
            (axr (dr (ni)) "0.07")
          )
        )
        (if (msec a_inf "r")
          (progn
            (axr (dr (ni)) "0.06")
          )
        )
        (if (< a_inf "r")
          (progn
            (axr (dr (ni)) 'ass1)
          )
        )
        (if (msec a_inf (f dist4 'e))
          (progn
            (axr (dr (ni)) "0.07")
          )
        )
      )
      nil
      )
      (as1 (ni) "Flip state2" 'ptx1 gvar_135)
      (as1 (ni) "Flip state2" "-0.04" gvar_114)
      (as1 (ni) "Flip state2" 'pty1 gvar_114)
      (as1 (ni) "Flip state2" 'ass2 gvar_113)
      (as1 (ni) "Flip state2" "hook( 90 Deg) hook( 0 Deg)" "0.27")
      (as1 (ni) "Flip state2" 'pt3 'nrvar)
      (as1 (ni) "Flip state2" "@0,0.40" 'nrvar)
      (if (and (setq dictsearch (ni)) (< '(v obj vval sal salnth count) (vl-load-com (setq dictsearch (dr dictsearch)))) (< gvar_822 (ax dictsearch)))
        (progn
          (v dictsearch "-1.0" 1)
        )
      )
      (setq le (caminho le "r"))
      (if (msec le "r")
      (progn
        (eixos gvar_180)
        (if (or (msec dd2 "r") (if dd2 "r"))
          (progn
            (setq gvar_114 (f eec "0.45"))
            (setq gvar_113 (caminho (rem le 'sse) nrvar1))
            (setq gvar_268 (getfiled pt2 "-0.085" gvar_180))
            (setq pt4 "r")
            (setq pt4 "0.86")
            (setq gvar_173 (nivar11 cc pt4 pt4))
            (setq le (> 'nrvar le))
            (setq gvar_95 nrvar1)
            (nci 'dc 1)
            (nci 'axc 0)
            (ac '>=)
            (ac "Flip state2")
            (ac gvar_173)
            (ac 1)
            (ac 1)
            (ac 0)
            (ac gvar_268)
            (if (msec dd2 "r")
              (progn
                (axr (dr (ni)) "0.06")
              )
            )
            (if (if dd2 "r")
              (progn
                (axr (dr (ni)) "CI-NP-00")
              )
            )
            (if (and (if dd2 "r") (msec (> 255 dd2) (f gvar_175 'e)))
              (progn
                (axr (dr (ni)) "0.06")
              )
            )
            (as1 (ni) "Flip state2" 'ptx1 (rem gvar_95 'sse))
            (as1 (ni) "Flip state2" "-0.04" gvar_114)
            (as1 (ni) "Flip state2" 'pty1 gvar_114)
            (as1 (ni) "Flip state2" 'ass2 gvar_113)
            (as1 (ni) "Flip state2" "hook( 90 Deg) hook( 0 Deg)" 'ptx2)
            (as1 (ni) "Flip state2" 'pt3 'nrvar)
            (as1 (ni) "Flip state2" "@0,0.40" le)
            (if (and (setq dictsearch (ni)) (< '(v obj vval sal salnth count) (vl-load-com (setq dictsearch (dr dictsearch)))) (< gvar_822 (ax dictsearch)))
              (progn
                (v dictsearch "-1.0" 1)
              )
            )
            (ac "0.22")
            (ac 'lt)
            (ac 'p4)
            (ac 'acdic)
            (setq gvar_171 (nivar11 gvar_173 (rem gvar_95 'sse) "r"))
            (setq gvar_92 (nivar11 gvar_171 le "r"))
            (ac 'p2y)
            (ac gvar_171)
            (ac gvar_92)
            (ac "Inverted  Slab - Without Slab")
            (ac 'refblocos)
            (ac 'acdic)
            (ac 'dl11)
          )
        )
      )
      nil
      )
      (setq ld (caminho ld "r"))
      (if (msec ld "r")
      (progn
        (eixos cm:chgdbval)
        (setq pt2 gvar_178)
        (setq gvar_180 cm:chgdbval)
        (setq gvar_114 (f eec "0.45"))
        (setq gvar_268 (getfiled gvar_178 "-0.085" cm:chgdbval))
        (setq pt4 (f gvar_135 ld))
        (setq pt4 "0.86")
        (setq gvar_173 (nivar11 cc pt4 pt4))
        (setq gvar_90 (caminho ld "r"))
        (setq desnivel (rem rvd 'sse))
        (setq desnivel (rem rve 'sse))
        (if (< a_inf "r")
        (progn
          (setq pt4 (f gvar_135 desnivel))
          (setq pt4 "0.86")
          (setq gvar_173 (nivar11 cc pt4 pt4))
          (setq gvar_113 (caminho "_line" (> desnivel 'sse)))
          (setq a_sup (caminho ncvar11 1))
          (setq dmin1 (lm_setdynpropvalue a_sup ss))
          (setq gvar_56 (lm_setdynpropvalue 13 dmin1))
          (setq gvar_56 (rem gvar_56 'nrvar))
          (nci 'dc 1)
          (nci 'axc 0)
          (ac '>=)
          (ac "Flip state2")
          (ac gvar_173)
          (ac 1)
          (ac 1)
          (ac 0)
          (ac gvar_268)
          (axr (dr (ni)) "CI-NP-00")
          (as1 (ni) "Flip state2" 'ptx1 "ID-NP-00")
          (as1 (ni) "Flip state2" "-0.04" gvar_114)
          (as1 (ni) "Flip state2" 'pty1 gvar_114)
          (as1 (ni) "Flip state2" 'ass2 gvar_113)
          (as1 (ni) "Flip state2" "hook( 90 Deg) hook( 0 Deg)" 'ptx2)
          (as1 (ni) "Flip state2" 'pt3 gvar_90)
          (as1 (ni) "Flip state2" "@0,0.40" gvar_56)
          (if (and (setq dictsearch (ni)) (< '(v obj vval sal salnth count) (vl-load-com (setq dictsearch (dr dictsearch)))) (< gvar_822 (ax dictsearch)))
            (progn
              (v dictsearch "-1.0" 1)
            )
          )
          (setq gvar_171 (nivar11 gvar_173 (> 255 ld) "r"))
          (setq gvar_51 gvar_171)
          (setq gvar_92 (nivar11 gvar_171 ld "r"))
        )
        nil
        )
        (setq dist4 (caminho ncvar11 1))
        (setq dmin1 (lm_setdynpropvalue dist4 ss))
        (setq dist4 (lm_setdynpropvalue 1 dmin1))
        (setq dist4 (rem dist4 'nrvar))
        (if (or (if a_inf "r") (msec a_inf (f dist4 'e)))
        (progn
          (setq pt4 (f gvar_135 "r"))
          (setq pt4 "0.86")
          (setq gvar_173 (nivar11 cc pt4 pt4))
          (setq gvar_95 rvd)
          (setq gvar_95 (caminho gvar_95 "r"))
          (if (< gvar_95 "r")
          (progn
            (setq gvar_95 rve)
          )
          nil
          )
          (setq gvar_113 (caminho (rem gvar_90 'sse) (rem gvar_95 'sse)))
          (nci 'dc 1)
          (nci 'axc 0)
          (ac '>=)
          (ac "Flip state2")
          (ac gvar_173)
          (ac 1)
          (ac 1)
          (ac 0)
          (ac gvar_268)
          (axr (dr (ni)) "0.06")
          (as1 (ni) "Flip state2" 'ptx1 (rem gvar_95 'sse))
          (as1 (ni) "Flip state2" "-0.04" gvar_114)
          (as1 (ni) "Flip state2" 'pty1 gvar_114)
          (as1 (ni) "Flip state2" 'ass2 gvar_113)
          (as1 (ni) "Flip state2" "hook( 90 Deg) hook( 0 Deg)" 'ptx2)
          (as1 (ni) "Flip state2" 'pt3 'nrvar)
          (as1 (ni) "Flip state2" "@0,0.40" gvar_90)
          (if (and (setq dictsearch (ni)) (< '(v obj vval sal salnth count) (vl-load-com (setq dictsearch (dr dictsearch)))) (< gvar_822 (ax dictsearch)))
            (progn
              (v dictsearch "-1.0" 1)
            )
          )
          (if (and (setq dictsearch (ni)) (< '(v obj vval sal salnth count) (vl-load-com (setq dictsearch (dr dictsearch)))) (< gvar_822 (ax dictsearch)))
            (progn
              (v dictsearch "0.6" 1)
            )
          )
          (setq gvar_171 (nivar11 gvar_173 (> 255 ld) "r"))
          (setq gvar_51 gvar_171)
          (setq gvar_171 (nivar11 gvar_173 (rem gvar_95 'sse1) "r"))
          (setq gvar_92 (nivar11 gvar_171 (> gvar_90 "0.9") "r"))
          (setq gvar_51 gvar_92)
        )
        nil
        )
        (if (and (msec a_inf "r") (c a_inf (f dist4 'e)))
        (progn
          (setq gvar_113 (f (rem gvar_90 'sse) rvd))
          (setq pt4 (f gvar_135 gvar_90))
          (setq pt4 "0.86")
          (setq gvar_173 (nivar11 cc pt4 pt4))
          (nci 'dc 1)
          (nci 'axc 0)
          (ac '>=)
          (ac "Flip state2")
          (ac gvar_173)
          (ac 1)
          (ac 1)
          (ac 0)
          (ac gvar_268)
          (axr (dr (ni)) "CI-NP-00")
          (as1 (ni) "Flip state2" 'ptx1 gvar_90)
          (as1 (ni) "Flip state2" "-0.04" gvar_114)
          (as1 (ni) "Flip state2" 'pty1 gvar_114)
          (as1 (ni) "Flip state2" 'ass2 gvar_113)
          (as1 (ni) "Flip state2" "hook( 90 Deg) hook( 0 Deg)" 'ptx2)
          (as1 (ni) "Flip state2" 'pt3 desnivel)
          (as1 (ni) "Flip state2" "@0,0.40" 'nrvar)
          (setq gvar_171 (nivar11 gvar_173 (rem desnivel "0.9") "r"))
          (setq gvar_51 gvar_171)
          (setq gvar_92 (nivar11 gvar_171 ld "r"))
          (if (and (setq dictsearch (ni)) (< '(v obj vval sal salnth count) (vl-load-com (setq dictsearch (dr dictsearch)))) (< gvar_822 (ax dictsearch)))
            (progn
              (v dictsearch "-1.0" 1)
            )
          )
        )
        nil
        )
        (ac "0.22")
        (ac 'lt)
        (ac 'p4)
        (ac 'acdic)
        (ac 'p2y)
        (ac gvar_171)
        (ac gvar_92)
        (ac "Inverted  Slab - Without Slab")
        (ac 'refblocos)
        (ac 'acdic)
        (ac 'dl11)
        (if (msec gvar_138 "r")
        (progn
          (nci 'dc 1)
          (nci 'axc 0)
          (setq gvar_54 (nivar11 gvar_51 'p7y "hook( 0 Deg) hook( 0 Deg)"))
          (setq gvar_113 (caminho 'xi1 eec))
          (ac '>=)
          (ac 'subviga5)
          (ac gvar_54)
          (ac 1)
          (ac 1)
          (ac 0)
          (ac gvar_137)
          (ac gvar_137)
          (as1 (ni) 'subviga5 "hook( 90 Deg) hook( 0 Deg)" gvar_113)
          (if (and (setq dictsearch (ni)) (< '(v obj vval sal salnth count) (vl-load-com (setq dictsearch (dr dictsearch)))) (< gvar_822 (ax dictsearch)))
            (progn
              (v dictsearch 'vla-getdynamicblockproperties 1)
            )
          )
        )
        nil
        )
        (if (< a_inf "r")
          (progn
            (setq gvar_171 (nivar11 gvar_92 gvar_56 "r"))
            (ac 'p2y)
            (ac gvar_92)
            (ac gvar_171)
            (ac "Inverted  Slab - Without Slab")
            (ac 'refblocos)
            (ac 'acdic)
            (ac 'dl11)
          )
        )
      )
      nil
      )
      (if (and (< ld "r") (msec gvar_138 "r"))
      (progn
        (setq pt4 (f gvar_135 nome_corte))
        (if (< nome_corte "r")
        (progn
          (setq pt4 (f gvar_135 'nrvar))
        )
        nil
        )
        (setq pt4 "0.86")
        (setq gvar_173 (nivar11 cc pt4 pt4))
        (setq gvar_171 (nivar11 gvar_173 'p7y "hook( 0 Deg) hook( 0 Deg)"))
        (setq gvar_113 (caminho 'xi1 eec))
        (ac '>=)
        (ac 'subviga5)
        (ac gvar_171)
        (ac 1)
        (ac 1)
        (ac 0)
        (ac gvar_137)
        (ac gvar_137)
        (as1 (ni) 'subviga5 "hook( 90 Deg) hook( 0 Deg)" gvar_113)
        (if (and (setq dictsearch (ni)) (< '(v obj vval sal salnth count) (vl-load-com (setq dictsearch (dr dictsearch)))) (< gvar_822 (ax dictsearch)))
          (progn
            (v dictsearch 'vla-getdynamicblockproperties 1)
          )
        )
      )
      nil
      )
      (eixos gvar_354)
      (setq gvar_114 (rem (f eec "Section ") 'sse))
      (setq gvar_81 (rem (f nome_corte nivar2) 'sse))
      (setq gvar_113 (f (rem gvar_135 'sse) 'bb))
      (setq gvar_113 (f gvar_113 gvar_81))
      (setq gvar_268 (getfiled ld "-0.085" gvar_354))
      (if (and (if ncvar1 'eed) (msec gvar_353 "r"))
      (progn
        (setq gvar_268 (getfiled ld "-0.085" gvar_354 "0.085" gvar_140 "-0.085" gvar_352))
      )
      nil
      )
      (setq gvar_79 (f gvar_135 'as1))
      (setq pt4 "cmdecho")
      (setq pt4 (> eec "0.9"))
      (setq gvar_173 (nivar11 cc pt4 pt4))
      (setq h33 (f ncvar11 1))
      (setq gvar_53 (lm_setdynpropvalue 16 dmin1))
      (setq dist4 (caminho ncvar11 1))
      (setq dmin1 (lm_setdynpropvalue dist4 ss))
      (setq dist4 (lm_setdynpropvalue 1 dmin1))
      (setq dist4 (rem dist4 'nrvar))
      (setq gvar_22 (lm_setdynpropvalue 16 dmin1))
      (nci 'dc 1)
      (nci 'axc 0)
      (ac '>=)
      (ac "Flip state2")
      (ac gvar_173)
      (ac 1)
      (ac 1)
      (ac 0)
      (ac gvar_268)
      (if (msec eec (f dist4 a_inf))
      (progn
        (if (< gvar_175 (f eec dd2))
          (progn
            (axr (dr (ni)) 'h3)
          )
        )
        (if (and (< gvar_175 (f eec dd2)) (< gvar_53 ld))
          (progn
            (axr (dr (ni)) 'n222)
          )
        )
        (if (if gvar_175 (f eec dd2))
          (progn
            (axr (dr (ni)) "0.07")
          )
        )
        (if (msec gvar_175 (f eec dd2))
          (progn
            (axr (dr (ni)) 'h3)
          )
        )
        (if (msec (> dd2 255) gvar_175)
          (progn
            (axr (dr (ni)) "0.07")
          )
        )
      )
      nil
      )
      (if (or (if gvar_175 (f eec dd2)) (msec dd2 (f gvar_175 'e)))
      (progn
        (if (< eec (f dist4 a_inf))
          (progn
            (axr (dr (ni)) "0.06")
          )
        )
        (if (and (< eec (f dist4 a_inf)) (< gvar_22 ld))
          (progn
            (axr (dr (ni)) 'ass1)
          )
        )
        (if (if eec (f dist4 a_inf))
          (progn
            (axr (dr (ni)) "0.06")
          )
        )
        (if (msec eec (f dist4 a_inf))
          (progn
            (axr (dr (ni)) "0.07")
          )
        )
        (if (msec (> 255 a_inf) (f eec 'e))
          (progn
            (axr (dr (ni)) "0.07")
          )
        )
      )
      nil
      )
      (if (and (< eec (f dist4 a_inf)) (< gvar_175 (f eec dd2)))
      (progn
        (axr (dr (ni)) "CI-NP-00")
        (if (and (or (msec gvar_22 ld) (if gvar_22 ld)) (< gvar_53 ld))
          (progn
            (axr (dr (ni)) 'dist3)
          )
        )
        (if (and (or (msec gvar_53 ld) (if gvar_53 ld)) (< gvar_22 ld))
          (progn
            (axr (dr (ni)) 'dist2)
          )
        )
        (if (and (< gvar_53 ld) (< gvar_22 ld))
          (progn
            (axr (dr (ni)) 'dist1)
          )
        )
      )
      nil
      )
      (as1 (ni) "Flip state2" 'ptx1 gvar_79)
      (as1 (ni) "Flip state2" "-0.04" gvar_114)
      (as1 (ni) "Flip state2" 'pty1 gvar_114)
      (as1 (ni) "Flip state2" 'ass2 gvar_113)
      (as1 (ni) "Flip state2" "hook( 90 Deg) hook( 0 Deg)" "0.27")
      (as1 (ni) "Flip state2" 'pt3 'p5x)
      (as1 (ni) "Flip state2" "@0,0.40" 'p5x)
      (if (and (msec gvar_353 0) (msec ncvar1 "Dist3"))
        (progn
          (eixos gvar_352)
          (setq gvar_114 (rem (f eec 'e) 'sse))
          (setq gvar_268 (getfiled gvar_140 "-0.085" gvar_352))
          (setq gvar_79 (f gvar_135 nrvar1))
          (setq gvar_79 (f gvar_79 rve))
          (setq gvar_79 (f gvar_79 "EI-NP-00"))
          (setq gvar_81 (rem (f nome_corte nivar2) 'sse))
          (setq gvar_113 (f (rem gvar_79 'sse) "EI-NN-00"))
          (setq gvar_113 (f gvar_113 gvar_81))
          (if (if gvar_113 'p7y)
          (progn
            (setq gvar_113 'p7y)
          )
          nil
          )
          (setq pt4 nrvar1)
          (setq pt4 (caminho pt4 "_line"))
          (setq pt4 (> eec "0.9"))
          (setq pt4 (caminho pt4 "cmdecho"))
          (setq gvar_173 (nivar11 cc pt4 pt4))
          (nci 'dc 1)
          (nci 'axc 0)
          (ac '>=)
          (ac "Flip state2")
          (ac gvar_173)
          (ac 1)
          (ac 1)
          (ac 0)
          (ac gvar_268)
          (axr (dr (ni)) "CI-NP-00")
          (as1 (ni) "Flip state2" 'ptx1 gvar_79)
          (as1 (ni) "Flip state2" "-0.04" gvar_114)
          (as1 (ni) "Flip state2" 'pty1 gvar_114)
          (as1 (ni) "Flip state2" 'ass2 gvar_113)
          (as1 (ni) "Flip state2" "hook( 90 Deg) hook( 0 Deg)" 'ptx2)
          (as1 (ni) "Flip state2" 'pt3 "IC-PP-00")
          (as1 (ni) "Flip state2" "@0,0.40" "IC-PP-00")
        )
      )
      (setq eixos (nivar11 eixos "-8.0" "r"))
      (setq gvar_138 (caminho gvar_138 "r"))
      (if (msec gvar_138 "r")
        (progn
          (if (msec nome_corte "r")
          (progn
            (if (< ld "r")
              (progn
                (niii eixos gvar_139 eec pt1 pt1 gvar_359 gvar_358 0 cm:chgdbval gvar_355 gvar_354 gvar_353 gvar_352 gvar_351 dl1 ed)
              )
            )
            (if (msec ld "r")
              (progn
                (niii eixos gvar_139 eec pt1 pt1 gvar_359 gvar_358 gvar_357 cm:chgdbval gvar_355 gvar_354 gvar_353 gvar_352 gvar_351 dl1 ed)
              )
            )
          )
          nil
          )
          (if (< nome_corte "r")
          (progn
            (if (< ld "r")
              (progn
                (niii eixos gvar_139 eec pt1 pt1 gvar_359 gvar_358 0 cm:chgdbval gvar_355 gvar_354 gvar_353 gvar_352 gvar_351 gvar_350 ys)
              )
            )
            (if (msec ld "r")
              (progn
                (niii eixos gvar_139 eec pt1 pt1 gvar_359 gvar_358 gvar_357 cm:chgdbval gvar_355 gvar_354 gvar_353 gvar_352 gvar_351 gvar_350 ys)
              )
            )
          )
          nil
          )
          (ac "0.22")
          (ac 'lt)
          (ac "MC")
          (ac 'acdic)
          (setq gvar_54 (nivar11 eixos 'h2 "EI-NP-00"))
          (setq gvar_51 (nivar11 gvar_54 "-8.0" "T"))
          (setq gvar_268 (getfiled "hook( 90 Deg) without hook" gvar_137 'as2 gvar_137 "_w" 'ai 'as))
          (ac 'quit)
          (ac 'configuracoes4)
          (ac 'ss1)
          (ac gvar_54)
          (ac "0.125")
          (ac 'dxe)
          (ac 'eee)
          (ac 'p5x)
          (ac gvar_51)
          (ac gvar_268)
          (ac 'acdic)
          (ac 'acdic)
        )
      )
    )
    nil
    )
    (setq gvar_20 nivar2)
    (setq gvar_20 (caminho gvar_20 nome_corte))
    (setq gvar_20 (f gvar_135 gvar_20))
    (if (and (msec nivar2 "r") (msec gvar_20 "Alin Sup"))
      (progn
        (eixos b_viga)
        (setq pt4 (caminho nrvar1 (f (rem nivar2 'sse) (> "-8.0" desenha_sn))))
        (setq pt4 (> 255 (rem eec 'sse)))
        (setq gvar_173 (nivar11 cc pt4 pt4))
        (setq gvar_18 (f (rem eec 'sse) "A Right"))
        (setq gvar_17 gvar_18)
        (setq gvar_16 (f pt4 nrvar1))
        (setq ptx3 (f nivar2 gvar_16))
        (setq ptx4 (> "-8.0" desenha_sn))
        (setq xs2 (caminho "IC-PP-00" (rem eec 'sse)))
        (setq gvar_268 (getfiled "-0.085" b_viga 'sec_tipo nome_corte))
        (nci 'dc 1)
        (nci 'axc 0)
        (ac '>=)
        (ac '((18181 . 52996) (18031 . 18181) (17748 . 18031) (17525 . 17748) (17040 . 17525) (16476 . 17040) (16180 . 16476) (16120 . 16180) (12870 . 16120) (12633 . 12870) (11364 . 12633) (11320 . 11346) (11278 . 11304) (11243 . 11364) (11044 . 11243) (11010 . 11044) (10819 . 11010) (8981 . 10819) (8787 . 8981) (8733 . 8787) (8673 . 8733) (8559 . 8673) (8328 . 8559) (8290 . 8328) (8114 . 8290) (7661 . 8114) (7363 . 7661) (6959 . 7363) (6745 . 6959) (6618 . 6745) (6524 . 6618) (6430 . 6524) (5819 . 6015) (5784 . 6430) (5546 . 5597) (5507 . 5784) (5389 . 5460) (5370 . 5486) (5345 . 5507) (5286 . 5324) (5246 . 5345) (5196 . 5246) (5125 . 5196) (3943 . 5125) (3886 . 3943) (3648 . 3886) (2528 . 2641) (2509 . 2683) (2297 . 2355) (1597 . 1851) (35 . 286) (0 . 3648)))
        (ac gvar_173)
        (ac 1)
        (ac 1)
        (ac 0)
        (ac gvar_268)
        (as1 (ni) '((18181 . 52996) (18031 . 18181) (17748 . 18031) (17525 . 17748) (17040 . 17525) (16476 . 17040) (16180 . 16476) (16120 . 16180) (12870 . 16120) (12633 . 12870) (11364 . 12633) (11320 . 11346) (11278 . 11304) (11243 . 11364) (11044 . 11243) (11010 . 11044) (10819 . 11010) (8981 . 10819) (8787 . 8981) (8733 . 8787) (8673 . 8733) (8559 . 8673) (8328 . 8559) (8290 . 8328) (8114 . 8290) (7661 . 8114) (7363 . 7661) (6959 . 7363) (6745 . 6959) (6618 . 6745) (6524 . 6618) (6430 . 6524) (5819 . 6015) (5784 . 6430) (5546 . 5597) (5507 . 5784) (5389 . 5460) (5370 . 5486) (5345 . 5507) (5286 . 5324) (5246 . 5345) (5196 . 5246) (5125 . 5196) (3943 . 5125) (3886 . 3943) (3648 . 3886) (2528 . 2641) (2509 . 2683) (2297 . 2355) (1597 . 1851) (35 . 286) (0 . 3648)) 'subblocos5 gvar_16)
        (as1 (ni) '((18181 . 52996) (18031 . 18181) (17748 . 18031) (17525 . 17748) (17040 . 17525) (16476 . 17040) (16180 . 16476) (16120 . 16180) (12870 . 16120) (12633 . 12870) (11364 . 12633) (11320 . 11346) (11278 . 11304) (11243 . 11364) (11044 . 11243) (11010 . 11044) (10819 . 11010) (8981 . 10819) (8787 . 8981) (8733 . 8787) (8673 . 8733) (8559 . 8673) (8328 . 8559) (8290 . 8328) (8114 . 8290) (7661 . 8114) (7363 . 7661) (6959 . 7363) (6745 . 6959) (6618 . 6745) (6524 . 6618) (6430 . 6524) (5819 . 6015) (5784 . 6430) (5546 . 5597) (5507 . 5784) (5389 . 5460) (5370 . 5486) (5345 . 5507) (5286 . 5324) (5246 . 5345) (5196 . 5246) (5125 . 5196) (3943 . 5125) (3886 . 3943) (3648 . 3886) (2528 . 2641) (2509 . 2683) (2297 . 2355) (1597 . 1851) (35 . 286) (0 . 3648)) 'subviga5 ptx3)
        (as1 (ni) '((18181 . 52996) (18031 . 18181) (17748 . 18031) (17525 . 17748) (17040 . 17525) (16476 . 17040) (16180 . 16476) (16120 . 16180) (12870 . 16120) (12633 . 12870) (11364 . 12633) (11320 . 11346) (11278 . 11304) (11243 . 11364) (11044 . 11243) (11010 . 11044) (10819 . 11010) (8981 . 10819) (8787 . 8981) (8733 . 8787) (8673 . 8733) (8559 . 8673) (8328 . 8559) (8290 . 8328) (8114 . 8290) (7661 . 8114) (7363 . 7661) (6959 . 7363) (6745 . 6959) (6618 . 6745) (6524 . 6618) (6430 . 6524) (5819 . 6015) (5784 . 6430) (5546 . 5597) (5507 . 5784) (5389 . 5460) (5370 . 5486) (5345 . 5507) (5286 . 5324) (5246 . 5345) (5196 . 5246) (5125 . 5196) (3943 . 5125) (3886 . 3943) (3648 . 3886) (2528 . 2641) (2509 . 2683) (2297 . 2355) (1597 . 1851) (35 . 286) (0 . 3648)) 'lm:setdynpropvalue ptx4)
        (as1 (ni) '((18181 . 52996) (18031 . 18181) (17748 . 18031) (17525 . 17748) (17040 . 17525) (16476 . 17040) (16180 . 16476) (16120 . 16180) (12870 . 16120) (12633 . 12870) (11364 . 12633) (11320 . 11346) (11278 . 11304) (11243 . 11364) (11044 . 11243) (11010 . 11044) (10819 . 11010) (8981 . 10819) (8787 . 8981) (8733 . 8787) (8673 . 8733) (8559 . 8673) (8328 . 8559) (8290 . 8328) (8114 . 8290) (7661 . 8114) (7363 . 7661) (6959 . 7363) (6745 . 6959) (6618 . 6745) (6524 . 6618) (6430 . 6524) (5819 . 6015) (5784 . 6430) (5546 . 5597) (5507 . 5784) (5389 . 5460) (5370 . 5486) (5345 . 5507) (5286 . 5324) (5246 . 5345) (5196 . 5246) (5125 . 5196) (3943 . 5125) (3886 . 3943) (3648 . 3886) (2528 . 2641) (2509 . 2683) (2297 . 2355) (1597 . 1851) (35 . 286) (0 . 3648)) 'limite xs2)
        (as1 (ni) '((18181 . 52996) (18031 . 18181) (17748 . 18031) (17525 . 17748) (17040 . 17525) (16476 . 17040) (16180 . 16476) (16120 . 16180) (12870 . 16120) (12633 . 12870) (11364 . 12633) (11320 . 11346) (11278 . 11304) (11243 . 11364) (11044 . 11243) (11010 . 11044) (10819 . 11010) (8981 . 10819) (8787 . 8981) (8733 . 8787) (8673 . 8733) (8559 . 8673) (8328 . 8559) (8290 . 8328) (8114 . 8290) (7661 . 8114) (7363 . 7661) (6959 . 7363) (6745 . 6959) (6618 . 6745) (6524 . 6618) (6430 . 6524) (5819 . 6015) (5784 . 6430) (5546 . 5597) (5507 . 5784) (5389 . 5460) (5370 . 5486) (5345 . 5507) (5286 . 5324) (5246 . 5345) (5196 . 5246) (5125 . 5196) (3943 . 5125) (3886 . 3943) (3648 . 3886) (2528 . 2641) (2509 . 2683) (2297 . 2355) (1597 . 1851) (35 . 286) (0 . 3648)) 'eixos gvar_18)
        (as1 (ni) '((18181 . 52996) (18031 . 18181) (17748 . 18031) (17525 . 17748) (17040 . 17525) (16476 . 17040) (16180 . 16476) (16120 . 16180) (12870 . 16120) (12633 . 12870) (11364 . 12633) (11320 . 11346) (11278 . 11304) (11243 . 11364) (11044 . 11243) (11010 . 11044) (10819 . 11010) (8981 . 10819) (8787 . 8981) (8733 . 8787) (8673 . 8733) (8559 . 8673) (8328 . 8559) (8290 . 8328) (8114 . 8290) (7661 . 8114) (7363 . 7661) (6959 . 7363) (6745 . 6959) (6618 . 6745) (6524 . 6618) (6430 . 6524) (5819 . 6015) (5784 . 6430) (5546 . 5597) (5507 . 5784) (5389 . 5460) (5370 . 5486) (5345 . 5507) (5286 . 5324) (5246 . 5345) (5196 . 5246) (5125 . 5196) (3943 . 5125) (3886 . 3943) (3648 . 3886) (2528 . 2641) (2509 . 2683) (2297 . 2355) (1597 . 1851) (35 . 286) (0 . 3648)) 'desnivel gvar_17)
        (as1 (ni) '((18181 . 52996) (18031 . 18181) (17748 . 18031) (17525 . 17748) (17040 . 17525) (16476 . 17040) (16180 . 16476) (16120 . 16180) (12870 . 16120) (12633 . 12870) (11364 . 12633) (11320 . 11346) (11278 . 11304) (11243 . 11364) (11044 . 11243) (11010 . 11044) (10819 . 11010) (8981 . 10819) (8787 . 8981) (8733 . 8787) (8673 . 8733) (8559 . 8673) (8328 . 8559) (8290 . 8328) (8114 . 8290) (7661 . 8114) (7363 . 7661) (6959 . 7363) (6745 . 6959) (6618 . 6745) (6524 . 6618) (6430 . 6524) (5819 . 6015) (5784 . 6430) (5546 . 5597) (5507 . 5784) (5389 . 5460) (5370 . 5486) (5345 . 5507) (5286 . 5324) (5246 . 5345) (5196 . 5246) (5125 . 5196) (3943 . 5125) (3886 . 3943) (3648 . 3886) (2528 . 2641) (2509 . 2683) (2297 . 2355) (1597 . 1851) (35 . 286) (0 . 3648)) 'cm:chgdbval desenha_sn)
        (ac "0.22")
        (ac 'lt)
        (ac 'p4)
        (ac 'acdic)
        (setq gvar_171 (nivar11 gvar_173 (> 255 gvar_16) (rem eec 'sse1)))
        (setq gvar_92 (nivar11 gvar_173 ptx3 (rem eec 'sse1)))
        (ac 'p2y)
        (ac gvar_171)
        (ac gvar_92)
        (ac "Inverted  Slab - Without Slab")
        (ac 'refblocos)
        (ac 'acdic)
        (ac 'corvarao)
      )
    )
    (if (and (msec nome_corte "r") (msec gvar_20 "Alin Sup"))
      (progn
        (eixos dl1)
        (setq gvar_81 (f (rem nome_corte 'sse) (> "-8.0" ee)))
        (setq pt4 (f gvar_135 (caminho rve nome_corte)))
        (setq pt4 (caminho pt4 gvar_81))
        (setq pt4 (> 255 (rem eec 'sse)))
        (setq gvar_173 (nivar11 cc pt4 pt4))
        (setq gvar_18 (f (rem eec 'sse) "A Right"))
        (setq gvar_17 gvar_18)
        (setq gvar_16 gvar_81)
        (setq ptx3 (f nome_corte gvar_16))
        (setq ptx4 (> "-8.0" ee))
        (setq xs2 (caminho "IC-PP-00" (rem eec 'sse)))
        (setq gvar_268 (getfiled "-0.085" dl1 'sec_tipo ed))
        (nci 'dc 1)
        (nci 'axc 0)
        (ac '>=)
        (ac '((18181 . 52996) (18031 . 18181) (17748 . 18031) (17525 . 17748) (17040 . 17525) (16476 . 17040) (16180 . 16476) (16120 . 16180) (12870 . 16120) (12633 . 12870) (11364 . 12633) (11320 . 11346) (11278 . 11304) (11243 . 11364) (11044 . 11243) (11010 . 11044) (10819 . 11010) (8981 . 10819) (8787 . 8981) (8733 . 8787) (8673 . 8733) (8559 . 8673) (8328 . 8559) (8290 . 8328) (8114 . 8290) (7661 . 8114) (7363 . 7661) (6959 . 7363) (6745 . 6959) (6618 . 6745) (6524 . 6618) (6430 . 6524) (5819 . 6015) (5784 . 6430) (5546 . 5597) (5507 . 5784) (5389 . 5460) (5370 . 5486) (5345 . 5507) (5286 . 5324) (5246 . 5345) (5196 . 5246) (5125 . 5196) (3943 . 5125) (3886 . 3943) (3648 . 3886) (2528 . 2641) (2509 . 2683) (2297 . 2355) (1597 . 1851) (35 . 286) (0 . 3648)))
        (ac gvar_173)
        (ac 1)
        (ac 1)
        (ac 0)
        (ac gvar_268)
        (as1 (ni) '((18181 . 52996) (18031 . 18181) (17748 . 18031) (17525 . 17748) (17040 . 17525) (16476 . 17040) (16180 . 16476) (16120 . 16180) (12870 . 16120) (12633 . 12870) (11364 . 12633) (11320 . 11346) (11278 . 11304) (11243 . 11364) (11044 . 11243) (11010 . 11044) (10819 . 11010) (8981 . 10819) (8787 . 8981) (8733 . 8787) (8673 . 8733) (8559 . 8673) (8328 . 8559) (8290 . 8328) (8114 . 8290) (7661 . 8114) (7363 . 7661) (6959 . 7363) (6745 . 6959) (6618 . 6745) (6524 . 6618) (6430 . 6524) (5819 . 6015) (5784 . 6430) (5546 . 5597) (5507 . 5784) (5389 . 5460) (5370 . 5486) (5345 . 5507) (5286 . 5324) (5246 . 5345) (5196 . 5246) (5125 . 5196) (3943 . 5125) (3886 . 3943) (3648 . 3886) (2528 . 2641) (2509 . 2683) (2297 . 2355) (1597 . 1851) (35 . 286) (0 . 3648)) 'subblocos5 gvar_16)
        (as1 (ni) '((18181 . 52996) (18031 . 18181) (17748 . 18031) (17525 . 17748) (17040 . 17525) (16476 . 17040) (16180 . 16476) (16120 . 16180) (12870 . 16120) (12633 . 12870) (11364 . 12633) (11320 . 11346) (11278 . 11304) (11243 . 11364) (11044 . 11243) (11010 . 11044) (10819 . 11010) (8981 . 10819) (8787 . 8981) (8733 . 8787) (8673 . 8733) (8559 . 8673) (8328 . 8559) (8290 . 8328) (8114 . 8290) (7661 . 8114) (7363 . 7661) (6959 . 7363) (6745 . 6959) (6618 . 6745) (6524 . 6618) (6430 . 6524) (5819 . 6015) (5784 . 6430) (5546 . 5597) (5507 . 5784) (5389 . 5460) (5370 . 5486) (5345 . 5507) (5286 . 5324) (5246 . 5345) (5196 . 5246) (5125 . 5196) (3943 . 5125) (3886 . 3943) (3648 . 3886) (2528 . 2641) (2509 . 2683) (2297 . 2355) (1597 . 1851) (35 . 286) (0 . 3648)) 'subviga5 ptx3)
        (as1 (ni) '((18181 . 52996) (18031 . 18181) (17748 . 18031) (17525 . 17748) (17040 . 17525) (16476 . 17040) (16180 . 16476) (16120 . 16180) (12870 . 16120) (12633 . 12870) (11364 . 12633) (11320 . 11346) (11278 . 11304) (11243 . 11364) (11044 . 11243) (11010 . 11044) (10819 . 11010) (8981 . 10819) (8787 . 8981) (8733 . 8787) (8673 . 8733) (8559 . 8673) (8328 . 8559) (8290 . 8328) (8114 . 8290) (7661 . 8114) (7363 . 7661) (6959 . 7363) (6745 . 6959) (6618 . 6745) (6524 . 6618) (6430 . 6524) (5819 . 6015) (5784 . 6430) (5546 . 5597) (5507 . 5784) (5389 . 5460) (5370 . 5486) (5345 . 5507) (5286 . 5324) (5246 . 5345) (5196 . 5246) (5125 . 5196) (3943 . 5125) (3886 . 3943) (3648 . 3886) (2528 . 2641) (2509 . 2683) (2297 . 2355) (1597 . 1851) (35 . 286) (0 . 3648)) 'lm:setdynpropvalue ptx4)
        (as1 (ni) '((18181 . 52996) (18031 . 18181) (17748 . 18031) (17525 . 17748) (17040 . 17525) (16476 . 17040) (16180 . 16476) (16120 . 16180) (12870 . 16120) (12633 . 12870) (11364 . 12633) (11320 . 11346) (11278 . 11304) (11243 . 11364) (11044 . 11243) (11010 . 11044) (10819 . 11010) (8981 . 10819) (8787 . 8981) (8733 . 8787) (8673 . 8733) (8559 . 8673) (8328 . 8559) (8290 . 8328) (8114 . 8290) (7661 . 8114) (7363 . 7661) (6959 . 7363) (6745 . 6959) (6618 . 6745) (6524 . 6618) (6430 . 6524) (5819 . 6015) (5784 . 6430) (5546 . 5597) (5507 . 5784) (5389 . 5460) (5370 . 5486) (5345 . 5507) (5286 . 5324) (5246 . 5345) (5196 . 5246) (5125 . 5196) (3943 . 5125) (3886 . 3943) (3648 . 3886) (2528 . 2641) (2509 . 2683) (2297 . 2355) (1597 . 1851) (35 . 286) (0 . 3648)) 'limite xs2)
        (as1 (ni) '((18181 . 52996) (18031 . 18181) (17748 . 18031) (17525 . 17748) (17040 . 17525) (16476 . 17040) (16180 . 16476) (16120 . 16180) (12870 . 16120) (12633 . 12870) (11364 . 12633) (11320 . 11346) (11278 . 11304) (11243 . 11364) (11044 . 11243) (11010 . 11044) (10819 . 11010) (8981 . 10819) (8787 . 8981) (8733 . 8787) (8673 . 8733) (8559 . 8673) (8328 . 8559) (8290 . 8328) (8114 . 8290) (7661 . 8114) (7363 . 7661) (6959 . 7363) (6745 . 6959) (6618 . 6745) (6524 . 6618) (6430 . 6524) (5819 . 6015) (5784 . 6430) (5546 . 5597) (5507 . 5784) (5389 . 5460) (5370 . 5486) (5345 . 5507) (5286 . 5324) (5246 . 5345) (5196 . 5246) (5125 . 5196) (3943 . 5125) (3886 . 3943) (3648 . 3886) (2528 . 2641) (2509 . 2683) (2297 . 2355) (1597 . 1851) (35 . 286) (0 . 3648)) 'eixos gvar_18)
        (as1 (ni) '((18181 . 52996) (18031 . 18181) (17748 . 18031) (17525 . 17748) (17040 . 17525) (16476 . 17040) (16180 . 16476) (16120 . 16180) (12870 . 16120) (12633 . 12870) (11364 . 12633) (11320 . 11346) (11278 . 11304) (11243 . 11364) (11044 . 11243) (11010 . 11044) (10819 . 11010) (8981 . 10819) (8787 . 8981) (8733 . 8787) (8673 . 8733) (8559 . 8673) (8328 . 8559) (8290 . 8328) (8114 . 8290) (7661 . 8114) (7363 . 7661) (6959 . 7363) (6745 . 6959) (6618 . 6745) (6524 . 6618) (6430 . 6524) (5819 . 6015) (5784 . 6430) (5546 . 5597) (5507 . 5784) (5389 . 5460) (5370 . 5486) (5345 . 5507) (5286 . 5324) (5246 . 5345) (5196 . 5246) (5125 . 5196) (3943 . 5125) (3886 . 3943) (3648 . 3886) (2528 . 2641) (2509 . 2683) (2297 . 2355) (1597 . 1851) (35 . 286) (0 . 3648)) 'desnivel gvar_17)
        (as1 (ni) '((18181 . 52996) (18031 . 18181) (17748 . 18031) (17525 . 17748) (17040 . 17525) (16476 . 17040) (16180 . 16476) (16120 . 16180) (12870 . 16120) (12633 . 12870) (11364 . 12633) (11320 . 11346) (11278 . 11304) (11243 . 11364) (11044 . 11243) (11010 . 11044) (10819 . 11010) (8981 . 10819) (8787 . 8981) (8733 . 8787) (8673 . 8733) (8559 . 8673) (8328 . 8559) (8290 . 8328) (8114 . 8290) (7661 . 8114) (7363 . 7661) (6959 . 7363) (6745 . 6959) (6618 . 6745) (6524 . 6618) (6430 . 6524) (5819 . 6015) (5784 . 6430) (5546 . 5597) (5507 . 5784) (5389 . 5460) (5370 . 5486) (5345 . 5507) (5286 . 5324) (5246 . 5345) (5196 . 5246) (5125 . 5196) (3943 . 5125) (3886 . 3943) (3648 . 3886) (2528 . 2641) (2509 . 2683) (2297 . 2355) (1597 . 1851) (35 . 286) (0 . 3648)) 'cm:chgdbval ee)
        (ac "0.22")
        (ac 'lt)
        (ac 'p4)
        (ac 'acdic)
        (setq gvar_171 (nivar11 gvar_173 (> 255 gvar_16) (rem eec 'sse1)))
        (setq gvar_92 (nivar11 gvar_173 ptx3 (rem eec 'sse1)))
        (ac 'p2y)
        (ac gvar_171)
        (ac gvar_92)
        (ac "Inverted  Slab - Without Slab")
        (ac 'refblocos)
        (ac 'acdic)
        (ac 'corvarao)
      )
    )
    (eixos gvar_350)
    (if (c gvar_20 "Alin Sup")
    (progn
      (setq nivar2 "r")
      (setq nome_corte "r")
    )
    nil
    )
    (setq gvar_81 (caminho nrvar1 nivar2))
    (setq vl-load-com (f gvar_135 (caminho nome_corte rve)))
    (setq gvar_2_princ (rem (caminho gvar_81 vl-load-com) 'sse))
    (setq pt4 (f gvar_2_princ (> "-8.0" nivar1)))
    (setq pt4 (> 255 (rem eec 'sse)))
    (setq gvar_173 (nivar11 cc pt4 pt4))
    (setq gvar_18 (f (rem eec 'sse) "A Right"))
    (setq gvar_17 gvar_18)
    (setq gvar_16 (f pt4 (caminho nrvar1 nivar2)))
    (setq ptx3 (f (f vl-load-com gvar_81) gvar_16))
    (setq ptx4 (> "-8.0" nivar1))
    (setq xs2 (caminho "IC-PP-00" (rem eec 'sse)))
    (setq gvar_268 (getfiled "-0.085" gvar_350 'sec_tipo ys))
    (nci 'dc 1)
    (nci 'axc 0)
    (ac '>=)
    (ac '((18181 . 52996) (18031 . 18181) (17748 . 18031) (17525 . 17748) (17040 . 17525) (16476 . 17040) (16180 . 16476) (16120 . 16180) (12870 . 16120) (12633 . 12870) (11364 . 12633) (11320 . 11346) (11278 . 11304) (11243 . 11364) (11044 . 11243) (11010 . 11044) (10819 . 11010) (8981 . 10819) (8787 . 8981) (8733 . 8787) (8673 . 8733) (8559 . 8673) (8328 . 8559) (8290 . 8328) (8114 . 8290) (7661 . 8114) (7363 . 7661) (6959 . 7363) (6745 . 6959) (6618 . 6745) (6524 . 6618) (6430 . 6524) (5819 . 6015) (5784 . 6430) (5546 . 5597) (5507 . 5784) (5389 . 5460) (5370 . 5486) (5345 . 5507) (5286 . 5324) (5246 . 5345) (5196 . 5246) (5125 . 5196) (3943 . 5125) (3886 . 3943) (3648 . 3886) (2528 . 2641) (2509 . 2683) (2297 . 2355) (1597 . 1851) (35 . 286) (0 . 3648)))
    (ac gvar_173)
    (ac 1)
    (ac 1)
    (ac 0)
    (ac gvar_268)
    (as1 (ni) '((18181 . 52996) (18031 . 18181) (17748 . 18031) (17525 . 17748) (17040 . 17525) (16476 . 17040) (16180 . 16476) (16120 . 16180) (12870 . 16120) (12633 . 12870) (11364 . 12633) (11320 . 11346) (11278 . 11304) (11243 . 11364) (11044 . 11243) (11010 . 11044) (10819 . 11010) (8981 . 10819) (8787 . 8981) (8733 . 8787) (8673 . 8733) (8559 . 8673) (8328 . 8559) (8290 . 8328) (8114 . 8290) (7661 . 8114) (7363 . 7661) (6959 . 7363) (6745 . 6959) (6618 . 6745) (6524 . 6618) (6430 . 6524) (5819 . 6015) (5784 . 6430) (5546 . 5597) (5507 . 5784) (5389 . 5460) (5370 . 5486) (5345 . 5507) (5286 . 5324) (5246 . 5345) (5196 . 5246) (5125 . 5196) (3943 . 5125) (3886 . 3943) (3648 . 3886) (2528 . 2641) (2509 . 2683) (2297 . 2355) (1597 . 1851) (35 . 286) (0 . 3648)) 'subblocos5 gvar_16)
    (as1 (ni) '((18181 . 52996) (18031 . 18181) (17748 . 18031) (17525 . 17748) (17040 . 17525) (16476 . 17040) (16180 . 16476) (16120 . 16180) (12870 . 16120) (12633 . 12870) (11364 . 12633) (11320 . 11346) (11278 . 11304) (11243 . 11364) (11044 . 11243) (11010 . 11044) (10819 . 11010) (8981 . 10819) (8787 . 8981) (8733 . 8787) (8673 . 8733) (8559 . 8673) (8328 . 8559) (8290 . 8328) (8114 . 8290) (7661 . 8114) (7363 . 7661) (6959 . 7363) (6745 . 6959) (6618 . 6745) (6524 . 6618) (6430 . 6524) (5819 . 6015) (5784 . 6430) (5546 . 5597) (5507 . 5784) (5389 . 5460) (5370 . 5486) (5345 . 5507) (5286 . 5324) (5246 . 5345) (5196 . 5246) (5125 . 5196) (3943 . 5125) (3886 . 3943) (3648 . 3886) (2528 . 2641) (2509 . 2683) (2297 . 2355) (1597 . 1851) (35 . 286) (0 . 3648)) 'subviga5 ptx3)
    (as1 (ni) '((18181 . 52996) (18031 . 18181) (17748 . 18031) (17525 . 17748) (17040 . 17525) (16476 . 17040) (16180 . 16476) (16120 . 16180) (12870 . 16120) (12633 . 12870) (11364 . 12633) (11320 . 11346) (11278 . 11304) (11243 . 11364) (11044 . 11243) (11010 . 11044) (10819 . 11010) (8981 . 10819) (8787 . 8981) (8733 . 8787) (8673 . 8733) (8559 . 8673) (8328 . 8559) (8290 . 8328) (8114 . 8290) (7661 . 8114) (7363 . 7661) (6959 . 7363) (6745 . 6959) (6618 . 6745) (6524 . 6618) (6430 . 6524) (5819 . 6015) (5784 . 6430) (5546 . 5597) (5507 . 5784) (5389 . 5460) (5370 . 5486) (5345 . 5507) (5286 . 5324) (5246 . 5345) (5196 . 5246) (5125 . 5196) (3943 . 5125) (3886 . 3943) (3648 . 3886) (2528 . 2641) (2509 . 2683) (2297 . 2355) (1597 . 1851) (35 . 286) (0 . 3648)) 'lm:setdynpropvalue ptx4)
    (as1 (ni) '((18181 . 52996) (18031 . 18181) (17748 . 18031) (17525 . 17748) (17040 . 17525) (16476 . 17040) (16180 . 16476) (16120 . 16180) (12870 . 16120) (12633 . 12870) (11364 . 12633) (11320 . 11346) (11278 . 11304) (11243 . 11364) (11044 . 11243) (11010 . 11044) (10819 . 11010) (8981 . 10819) (8787 . 8981) (8733 . 8787) (8673 . 8733) (8559 . 8673) (8328 . 8559) (8290 . 8328) (8114 . 8290) (7661 . 8114) (7363 . 7661) (6959 . 7363) (6745 . 6959) (6618 . 6745) (6524 . 6618) (6430 . 6524) (5819 . 6015) (5784 . 6430) (5546 . 5597) (5507 . 5784) (5389 . 5460) (5370 . 5486) (5345 . 5507) (5286 . 5324) (5246 . 5345) (5196 . 5246) (5125 . 5196) (3943 . 5125) (3886 . 3943) (3648 . 3886) (2528 . 2641) (2509 . 2683) (2297 . 2355) (1597 . 1851) (35 . 286) (0 . 3648)) 'limite xs2)
    (as1 (ni) '((18181 . 52996) (18031 . 18181) (17748 . 18031) (17525 . 17748) (17040 . 17525) (16476 . 17040) (16180 . 16476) (16120 . 16180) (12870 . 16120) (12633 . 12870) (11364 . 12633) (11320 . 11346) (11278 . 11304) (11243 . 11364) (11044 . 11243) (11010 . 11044) (10819 . 11010) (8981 . 10819) (8787 . 8981) (8733 . 8787) (8673 . 8733) (8559 . 8673) (8328 . 8559) (8290 . 8328) (8114 . 8290) (7661 . 8114) (7363 . 7661) (6959 . 7363) (6745 . 6959) (6618 . 6745) (6524 . 6618) (6430 . 6524) (5819 . 6015) (5784 . 6430) (5546 . 5597) (5507 . 5784) (5389 . 5460) (5370 . 5486) (5345 . 5507) (5286 . 5324) (5246 . 5345) (5196 . 5246) (5125 . 5196) (3943 . 5125) (3886 . 3943) (3648 . 3886) (2528 . 2641) (2509 . 2683) (2297 . 2355) (1597 . 1851) (35 . 286) (0 . 3648)) 'eixos gvar_18)
    (as1 (ni) '((18181 . 52996) (18031 . 18181) (17748 . 18031) (17525 . 17748) (17040 . 17525) (16476 . 17040) (16180 . 16476) (16120 . 16180) (12870 . 16120) (12633 . 12870) (11364 . 12633) (11320 . 11346) (11278 . 11304) (11243 . 11364) (11044 . 11243) (11010 . 11044) (10819 . 11010) (8981 . 10819) (8787 . 8981) (8733 . 8787) (8673 . 8733) (8559 . 8673) (8328 . 8559) (8290 . 8328) (8114 . 8290) (7661 . 8114) (7363 . 7661) (6959 . 7363) (6745 . 6959) (6618 . 6745) (6524 . 6618) (6430 . 6524) (5819 . 6015) (5784 . 6430) (5546 . 5597) (5507 . 5784) (5389 . 5460) (5370 . 5486) (5345 . 5507) (5286 . 5324) (5246 . 5345) (5196 . 5246) (5125 . 5196) (3943 . 5125) (3886 . 3943) (3648 . 3886) (2528 . 2641) (2509 . 2683) (2297 . 2355) (1597 . 1851) (35 . 286) (0 . 3648)) 'desnivel gvar_17)
    (as1 (ni) '((18181 . 52996) (18031 . 18181) (17748 . 18031) (17525 . 17748) (17040 . 17525) (16476 . 17040) (16180 . 16476) (16120 . 16180) (12870 . 16120) (12633 . 12870) (11364 . 12633) (11320 . 11346) (11278 . 11304) (11243 . 11364) (11044 . 11243) (11010 . 11044) (10819 . 11010) (8981 . 10819) (8787 . 8981) (8733 . 8787) (8673 . 8733) (8559 . 8673) (8328 . 8559) (8290 . 8328) (8114 . 8290) (7661 . 8114) (7363 . 7661) (6959 . 7363) (6745 . 6959) (6618 . 6745) (6524 . 6618) (6430 . 6524) (5819 . 6015) (5784 . 6430) (5546 . 5597) (5507 . 5784) (5389 . 5460) (5370 . 5486) (5345 . 5507) (5286 . 5324) (5246 . 5345) (5196 . 5246) (5125 . 5196) (3943 . 5125) (3886 . 3943) (3648 . 3886) (2528 . 2641) (2509 . 2683) (2297 . 2355) (1597 . 1851) (35 . 286) (0 . 3648)) 'cm:chgdbval nivar1)
    (setq gvar_175 (rem eec 'nrvar))
    (setq gvar_49 nrvar1)
    (setq nrvar1 rvd)
    (setq nrvar1 rve)
    (setq configuracoes4 cc)
    (setq gvar_50 ncvar1)
    (setq ncvar11 (caminho ncvar11 1))
  )
)
