(defun poz_edit_adet_carpi (tb / )
(fi_)
(setq position      0)
(setq position_last 0)
(setq fi_yeri (vl-string-search fi tb))
(setq fi_boyu (strlen fi))
(setq adet_kismi (substr tb 1 fi_yeri))
(if (and (> (strlen adet_kismi) 0 )
         (/= (vl-string-search "X" (strcase adet_kismi)) nil ))
       (progn
         (while (/= position nil)
          (if (/= position nil)
                (progn
                    (setq position_last (max position position_last))
                    (setq position (vl-string-search "X" (strcase adet_kismi) (1+ position)))
                 )
          )
         )
         (setq adet_carp (substr adet_kismi 1 position_last ))
       )
      (setq adet_carp "")
)
adet_carp
)
;--------------------------------------------------------------------------------------------------------------------------------------------------------
(defun poz_edit_adet (tb / )
(fi_)
(setq position      0)
(setq position_max  0)
(setq fi_yeri (vl-string-search fi tb))
(setq adet_kismi (substr tb 1 fi_yeri))
(if (> (strlen adet_kismi) 0 )
      (if (= (vl-string-search "X" (strcase adet_kismi)) nil)
       (setq adet adet_kismi)
       (progn
         (while (/= position nil)
          (if (/= position nil)
                (progn
                    (setq position_last (max position position_last))
                    (setq position (vl-string-search "X" (strcase adet_kismi) (1+ position)))
                 )
          )
         )
          (setq adet (substr adet_kismi (+ position_last 2)))
       )
      )
      (setq adet "")
)
adet
)
;--------------------------------------------------------------------------------------------------------------------------------------------------------
(defun poz_edit_cap (tb / )
(fi_)
(setq fi_boyu (strlen fi))
(setq fi_yeri (vl-string-search fi   tb      ))
(setq b_yeri  (vl-string-search "/"  tb      ))
(if (= b_yeri nil) (setq b_yeri (+ 1 (strlen tb))))
(setq cap (substr tb (+ 1 fi_boyu fi_yeri)  (- b_yeri  fi_yeri fi_boyu)))
cap
)
;--------------------------------------------------------------------------------------------------------------------------------------------------------
(defun poz_edit_aralik (tb / )
(fi_)
(setq fi_boyu  (strlen fi))
(setq tb_boyu  (strlen tb))
(setq b_yeri   (vl-string-search "/"  tb      ))
(if (/= b_yeri nil)
        (setq aralik_b   (substr tb (+ 2 b_yeri )  (- tb_boyu b_yeri)))
        (setq aralik_b ""))
aralik_b
)
;-------------------------------------------------------------------------------
(defun poz_key_act (/)
(poz_toplam_goruntu_guncelle)
(princ)
)
(defun p_arttir_key_act (/)
(setq poz (itoa (1+ (atoi (get_tile "poz_key")))))
(set_tile "poz_key" poz)
(poz_toplam_goruntu_guncelle)
(princ)
)
(defun p_azalt_key_act (/)
(setq poz (itoa (1- (atoi (get_tile "poz_key")))))
(set_tile "poz_key" poz)
(poz_toplam_goruntu_guncelle)
(princ)
)
;-------------------------------------------------------------------------------
(defun gc_key_act (/)
(setq grup_carpani (get_tile "gc_key"))
(if (< (atoi grup_carpani) 1) (set_tile "gc_key" "1"))
(princ)
)

(defun grup_c_arttir_key_act (/)
(setq grup_carpani (itoa (1+ (atoi (get_tile "gc_key")))))
(if (< (atoi grup_carpani) 1) (setq grup_carpani "1"))
(set_tile "gc_key" grup_carpani)
(princ)
)

(defun grup_c_azalt_key_act (/)
(setq grup_carpani (itoa (1- (atoi (get_tile "gc_key")))))
(if (< (atoi grup_carpani) 1) (setq grup_carpani "1"))
(set_tile "gc_key" grup_carpani)
(princ)
)
;-------------------------------------------------------------------------------
(defun adet_carp_key_act (/)
(poz_toplam_goruntu_guncelle)
(princ)
)

(defun adet_c_arttir_key_act (/)
(setq adet_carp (get_tile "adet_carp_key"))
(if (= (vl-string-search "x" (strcase adet_carp)) nil)
  (setq adet_carp (itoa (1+ (atoi adet_carp))))
  (progn
    (setq yer (vl-string-search "x" (strcase adet_carp)))
    (setq adet_carp (strcat (itoa (1+ (atoi (substr adet_carp 1 yer)))) (substr adet_carp (1+ yer) (strlen adet_carp))))
  )
)
(if (= adet_carp "0") (setq adet_carp ""))
(set_tile "adet_carp_key" adet_carp)
(poz_toplam_goruntu_guncelle)
(princ)
)

(defun adet_c_azalt_key_act (/)
(setq adet_carp (get_tile "adet_carp_key"))
(if (> (strlen adet_carp) 0)
(progn
(if (= (vl-string-search "x" (strcase adet_carp)) nil)
  (setq adet_carp (itoa (1- (atoi adet_carp))))
  (progn
    (setq yer (vl-string-search "x" (strcase adet_carp)))
    (if (> (1- (atoi (substr adet_carp 1 yer))) 0)
     (setq adet_carp (strcat (itoa (1- (atoi (substr adet_carp 1 yer)))) (substr adet_carp (1+ yer) (strlen adet_carp))))
     (setq adet_carp (substr adet_carp (+ 2 yer) (strlen adet_carp)))
    )
  )
)
(if (= adet_carp "0") (setq adet_carp ""))
))
(set_tile "adet_carp_key" adet_carp)
(poz_toplam_goruntu_guncelle)
(princ)
)
;-------------------------------------------------------------------------------
(defun adet_key_act (/)
(att_field_sil en "TB" )
(poz_toplam_goruntu_guncelle)
(princ)
)
;-------------------------------------------------------------------------------
(defun adet_arttir_key_act (/)
(att_field_sil en "TB" )
(setq adet (itoa (1+ (atoi (get_tile "adet_key")))))
(if (< (atoi adet) 1) (setq adet ""))
(set_tile "adet_key" adet)
(poz_toplam_goruntu_guncelle)
(princ)
)
;-------------------------------------------------------------------------------
(defun adet_azalt_key_act (/)
(att_field_sil en "TB" )
(if (> (strlen adet) 0)
(progn
(setq adet (itoa (1- (atoi (get_tile "adet_key")))))
(if (< (atoi adet) 1) (setq adet ""))
))
(set_tile "adet_key" adet)
(poz_toplam_goruntu_guncelle)
(princ)
)
;-------------------------------------------------------------------------------
(defun cap_key_act (/)
(set_tile "tik_key" "1")
(poz_toplam_goruntu_guncelle)
(princ)
)
(defun cap_arttir_key_act (/)
(if (or (= (get_tile "cap_key") "24") (= (get_tile "cap_key") "25"))
(setq cap (itoa (+ (atoi (get_tile "cap_key")) 1)))
(setq cap (itoa (+ (atoi (get_tile "cap_key")) 2)))
)
(if (> (atoi cap) 32) (setq cap "32"))
(if (< (atoi cap)  8) (setq cap  "8"))
(set_tile "tik_key" "1")
(set_tile "cap_key" cap)
(poz_toplam_goruntu_guncelle)
(princ)
)
(defun cap_azalt_key_act (/)
(if (or (= (get_tile "cap_key") "26") (= (get_tile "cap_key") "25"))
(setq cap (itoa (- (atoi (get_tile "cap_key")) 1)))
(setq cap (itoa (- (atoi (get_tile "cap_key")) 2)))
)
(if (> (atoi cap) 32) (setq cap "32"))
(if (< (atoi cap)  8) (setq cap  "8"))
(set_tile "tik_key" "1")
(set_tile "cap_key" cap)
(poz_toplam_goruntu_guncelle)
(princ)
)
;-------------------------------------------------------------------------------
(defun aralik_key_act (/)
(att_yaz en "ARALIK" (get_tile "aralik_key"))
(poz_toplam_goruntu_guncelle)
(princ)
)
;-------------------------------------------------------------------------------
(defun aralik_arttir_key_act (/)
(setq adim (fix (* (BIRIM_OKU) 0.05)))
(setq aralik (itoa (+ (atoi (get_tile "aralik_key")) adim )))
(if (< (atoi aralik)  1) (setq aralik  ""))
(set_tile "aralik_key" aralik)
(att_yaz en "ARALIK"   aralik)
(poz_toplam_goruntu_guncelle)
(princ)
)
;-------------------------------------------------------------------------------
(defun aralik_azalt_key_act (/)
(setq adim (fix (* (BIRIM_OKU) 0.05)))
(setq aralik (itoa (- (atoi (get_tile "aralik_key")) adim )))
(if (< (atoi aralik)  1) (setq aralik  ""))
(set_tile "aralik_key" aralik)
(att_yaz en "ARALIK"   aralik)
(poz_toplam_goruntu_guncelle)
(princ)
)
;-------------------------------------------------------------------------------
(defun boy_key_act (/)
(setq boy (get_tile "boy_key"))
(if (/= (strlen boy) 0)
(progn
(setq boy (vl-string-subst "" "L=" boy))
(setq boy (strcat "L=" boy))
(set_tile "boy_key" boy)))
(poz_toplam_goruntu_guncelle)
(princ)
)
;-------------------------------------------------------------------------------
(defun boy_hesapla_key_act (/)
(if (/= TIP "99")
 (progn
  (setq boy (b_h TIP BB_A BB_B BB_C BB_D BB_E BB_F (atof BB_R) (atof cap)))
  (set_tile "boy_key" boy)
 )
)
(princ)
)
;-------------------------------------------------------------------------------
(defun poz_toplam_goruntu_guncelle (/)
(setq b1 (get_tile "poz_key"       ))
(setq b2 (get_tile "adet_carp_key" ))
(setq b3 (get_tile "adet_key"      ))
(setq b4 (get_tile "cap_key"       ))
(setq b5 (get_tile "aralik_key"    ))
(setq b6 (get_tile "boy_key"       ))
(if (> (strlen b2) 0) (setq b2_ (strcat b2 "x" ))(setq b2_ ""))
(if (> (strlen b5) 0) (setq b5_ (strcat "/" b5 ))(setq b5_ ""))
(set_tile "poz_toplam_goruntu" (strcat "( " b1 " )   " b2_ b3 "\\U+00D8" b4 b5_ "   " b6))
)
;-------------------------------------------------------------------------------
(defun tip_key_act (/)
(set_tile "tik_key" "1")
(poz_toplam_goruntu_guncelle)
(princ)
)
(defun tip_liste_key_act (/)
(set_tile "tip_key" (nth (atoi (get_tile "tip_liste_key")) tip_liste))
(setq tip (get_tile "tip_key"))
(poz_image_key_act tip)
(set_tile "A_key"   "0")
(set_tile "B_key"   "0")
(set_tile "C_key"   "0")
(set_tile "D_key"   "0")
(set_tile "E_key"   "0")
(set_tile "F_key"   "0")
(set_tile "R_key"   "0")
(setq tik_bilgi "1")
(butun_degerleri_hafizaya_al)
(boy_hesapla_key_act)
(poz_toplam_goruntu_guncelle)
(princ)
)
(defun A_key_act (/)
(set_tile "tik_key" "1")
(butun_degerleri_hafizaya_al)
(boy_hesapla_key_act)
(poz_toplam_goruntu_guncelle)
(princ)
)
(defun B_key_act (/)
(set_tile "tik_key" "1")
(butun_degerleri_hafizaya_al)
(boy_hesapla_key_act)
(poz_toplam_goruntu_guncelle)
(princ)
)
(defun C_key_act (/)
(set_tile "tik_key" "1")
(butun_degerleri_hafizaya_al)
(boy_hesapla_key_act)
(poz_toplam_goruntu_guncelle)
(princ)
)
(defun D_key_act (/)
(set_tile "tik_key" "1")
(butun_degerleri_hafizaya_al)
(boy_hesapla_key_act)
(poz_toplam_goruntu_guncelle)
(princ)
)
(defun E_key_act (/)
(set_tile "tik_key" "1")
(butun_degerleri_hafizaya_al)
(boy_hesapla_key_act)
(poz_toplam_goruntu_guncelle)
(princ)
)
(defun F_key_act (/)
(set_tile "tik_key" "1")
(setq tik_bilgi "1")
(butun_degerleri_hafizaya_al)
(boy_hesapla_key_act)
(poz_toplam_goruntu_guncelle)
(princ)
)
(defun R_key_act (/)
(set_tile "tik_key" "1")
(butun_degerleri_hafizaya_al)
(boy_hesapla_key_act)
(poz_toplam_goruntu_guncelle)
(princ)
)
;-------------------------------------------------------------------------------
(defun malzeme_liste_key_act (/)
(set_tile "malzeme_key" (nth (atoi (get_tile "malzeme_liste_key")) malzeme_tur_listesi))
(setq malzeme_turu (get_tile "malzeme_key"))
(butun_degerleri_hafizaya_al)
(princ)
)
;-------------------------------------------------------------------------------
(defun butun_degerleri_hafizaya_al (/)
(setq poz           (get_tile "poz_key"       ))
(setq adet_carp     (get_tile "adet_carp_key" ))
(setq adet          (get_tile "adet_key"      ))
(setq cap           (get_tile "cap_key"       ))
(setq aralik        (get_tile "aralik_key"    ))
(setq boy           (get_tile "boy_key"       ))
(setq TIP           (get_tile "tip_key"       ))
(setq BB_A          (get_tile "A_key"         ))
(setq BB_B          (get_tile "B_key"         ))
(setq BB_C          (get_tile "C_key"         ))
(setq BB_D          (get_tile "D_key"         ))
(setq BB_E          (get_tile "E_key"         ))
(setq BB_F          (get_tile "F_key"         ))
(setq BB_R          (get_tile "R_key"         ))
(setq aciklama      (get_tile "not_key"       ))
(setq grup_carpani  (get_tile "gc_key"        ))
(setq malzeme_turu  (get_tile "malzeme_key"   ))
(setq tik_bilgi     (get_tile "tik_key"       ))
)
;
;-------------------------------------------------------------------------------
(defun tire_varsa_ekle ( eski yeni / )
(setq tire_mi (substr eski (strlen eski) 1))
(if (= tire_mi "-") (setq yeni (strcat eski yeni)))
yeni
)
;-------------------------------------------------------------------------------
(defun bukum_boyu_al ( / )
(if (= (BIRIM_OKU) 1000 ) (setq sayi_2 10) (setq sayi_2 1))
(SETQ yaz_olc      (GETVAR "DIMLFAC" ))
(setq b_en (car (entsel "\n Bukum boyu hesabi icin bir text veya line secin....  ")))
(if (/= b_en nil)
(progn
;
(setq b_boy2 "")
;
(if  (= (cdr (assoc 0 (entget b_en))) "TEXT")
 (progn
  (setq b_boy (atof (cdr (assoc 1 (entget b_en)))))
   (if (or (/= (vl-string-search "-" (cdr (assoc 1 (entget b_en))) 0 ) nil)
           (/= (vl-string-search "~" (cdr (assoc 1 (entget b_en))) 0 ) nil)
       )
     (setq b_boy2 (cdr (assoc 1 (entget b_en))))
   )
 )
)
;
(if  (= (cdr (assoc 0 (entget b_en))) "LINE")
(setq b_boy (* yaz_olc (distance (cdr (assoc 10 (entget b_en))) (cdr (assoc 11 (entget b_en)))))))
;
(if (or
     (= (cdr (assoc 0 (entget b_en))) "DIMENSION")
     (= (cdr (assoc 0 (entget b_en))) "ARC_DIMENSION")
     (= (cdr (assoc 0 (entget b_en))) "LARGE_RADIAL_DIMENSION")
    )
(setq b_boy (cdr (assoc 42 (entget b_en))))
)
;
(if  (= (cdr (assoc 0 (entget b_en))) "LWPOLYLINE" )
(setq b_boy (* yaz_olc (vlax-curve-getDistatParam b_en (vlax-curve-getEndParam b_en)))))
;
(if  (= (cdr (assoc 0 (entget b_en))) "ARC"        )
(setq b_boy (* yaz_olc (vlax-curve-getDistatParam b_en (vlax-curve-getEndParam b_en)))))
;
(setq b_boy  (float (* (fix (+ (/ b_boy sayi_2 ) 0.50 )) sayi_2 )))
(setq b_boy  (rtos b_boy 2 0))
(if (/= b_boy2 "") (setq b_boy b_boy2))
(COND
((= tile_name "A_key") (setq BB_A (tire_varsa_ekle BB_A b_boy)))
((= tile_name "B_key") (setq BB_B (tire_varsa_ekle BB_B b_boy)))
((= tile_name "C_key") (setq BB_C (tire_varsa_ekle BB_C b_boy)))
((= tile_name "D_key") (setq BB_D (tire_varsa_ekle BB_D b_boy)))
((= tile_name "E_key") (setq BB_E (tire_varsa_ekle BB_E b_boy)))
((= tile_name "F_key") (setq BB_F (tire_varsa_ekle BB_F b_boy)))
((= tile_name "R_key") (setq BB_R (tire_varsa_ekle BB_R b_boy)))
( T                    (princ)          )
)
)
(progn
(setq b_boy (getdist "\n Mesafe isaretleyin..."))
(if (= b_boy nil) (setq b_boy 0))
(setq b_boy  (rtos (* yaz_olc b_boy) 2 0))

(COND
((= tile_name "A_key") (setq BB_A (tire_varsa_ekle BB_A b_boy)))
((= tile_name "B_key") (setq BB_B (tire_varsa_ekle BB_B b_boy)))
((= tile_name "C_key") (setq BB_C (tire_varsa_ekle BB_C b_boy)))
((= tile_name "D_key") (setq BB_D (tire_varsa_ekle BB_D b_boy)))
((= tile_name "E_key") (setq BB_E (tire_varsa_ekle BB_E b_boy)))
((= tile_name "F_key") (setq BB_F (tire_varsa_ekle BB_F b_boy)))
((= tile_name "R_key") (setq BB_R (tire_varsa_ekle BB_R b_boy)))
( T                    (princ)          )
)

)
)
)
;-------------------------------------------------------------------------------
;
(defun a_al_key_act (/)
(set_tile "tik_key" "1")
(butun_degerleri_hafizaya_al)
(setq tile_name "A_key")
(done_dialog 5)
)
(defun b_al_key_act (/)
(set_tile "tik_key" "1")
(butun_degerleri_hafizaya_al)
(setq tile_name "B_key")
(done_dialog 5)
)
(defun c_al_key_act (/)
(set_tile "tik_key" "1")
(butun_degerleri_hafizaya_al)
(setq tile_name "C_key")
(done_dialog 5)
)
(defun d_al_key_act (/)
(set_tile "tik_key" "1")
(butun_degerleri_hafizaya_al)
(setq tile_name "D_key")
(done_dialog 5)
)
(defun e_al_key_act (/)
(set_tile "tik_key" "1")
(butun_degerleri_hafizaya_al)
(setq tile_name "E_key")
(done_dialog 5)
)
(defun f_al_key_act (/)
(set_tile "tik_key" "1")
(butun_degerleri_hafizaya_al)
(setq tile_name "F_key")
(done_dialog 5)
)
(defun r_al_key_act (/)
(set_tile "tik_key" "1")
(butun_degerleri_hafizaya_al)
(setq tile_name "R_key")
(done_dialog 5)
)
(defun tum_poz_gucelle_act (/)
(set_tile "tik_key" "1")
(butun_degerleri_hafizaya_al)
(done_dialog 7)
)
(defun tddk_al_key_act (/)
(set_tile "tik_key" "1")
(butun_degerleri_hafizaya_al)
(done_dialog 8)
)
;-------------------------------------------------------------------------------
;-------------------------------------------------------------------------------
;-------------------------------------------------------------------------------
(defun donati_tani_key_act (/)
(set_tile "tik_key" "1")
(butun_degerleri_hafizaya_al)
(done_dialog 11)
)
;-------------------------------------------------------------------------------
;-------------------------------------------------------------------------------
;-------------------------------------------------------------------------------
;- OTOMATİK DONATI TANIMA BÖLÜMÜ BURADA BAŞLIYOR.-------------------------------
;-------------------------------------------------------------------------------
;-------------------------------------------------------------------------------
;-------------------------------------------------------------------------------
(defun koordinat_dondur ( point teta / ) (list (- (* (Car point) (Cos teta)) (* (Cadr point) (Sin teta))) (+ (* (Car point) (Sin teta)) (* (Cadr point) (Cos teta))) (Caddr point)))
;-------------------------------------------------------------------------------
(defun pline_icin_arc_coz ( P01 P02 ARC_H / P01 P02 ARC_G )
(setq s_value (distance P01 P02))
(setq h_value (* (* 0.5 s_value) ARC_H))
(setq r_value (+ (* 0.5 h_value)  (/ (* s_value s_value) (* 8 h_value))))
(setq a_value (* 4 (atan ARC_H)))
(setq b_value (* r_value a_value))
;(setq BB_A  (rtos (float (* (fix (+ (/ (* OLCEK b_value) SAYI) 0.5)) SAYI)) 2 0))
;(setq BB_B  (rtos (float (* (fix (+ (/ (* OLCEK s_value) SAYI) 0.5)) SAYI)) 2 0))
;(setq BB_C  (rtos (float (* (fix (+ (/ (* OLCEK h_value) SAYI) 0.5)) SAYI)) 2 0))
;(setq BB_R  (rtos (float (* (fix (+ (/ (* OLCEK r_value) SAYI) 0.5)) SAYI)) 2 0))
(princ)
)
;-------------------------------------------------------------------------------
(defun arc_coz ( e / e P01 P02 ARC_G )
(setq r_value (cdr (assoc 40  (entget e))))
(setq cevre1  (cdr (assoc 50  (entget e))))
(if (= cevre1 nil) (setq cevre1 0))
(setq cevre2  (cdr (assoc 51  (entget e))))
(if (< cevre2 cevre1) (setq cevre2 (+ cevre2 6.283185307)))
(setq cevre3  (- cevre2 cevre1))
(setq b_value (* cevre3 (cdr (assoc 40  (entget e)))))
(setq P01 (polar (cdr (assoc 10  (entget e))) (cdr (assoc 50  (entget e))) (cdr (assoc 40  (entget e)))))
(setq P02 (polar (cdr (assoc 10  (entget e))) (cdr (assoc 51  (entget e))) (cdr (assoc 40  (entget e)))))
(setq s_value (distance P01 P02))
(setq P03 (polar P01 (angle P01 P02) (/ (distance P01 P02) 2.0)))
(setq h_value (- r_value (distance P03 (cdr (assoc 10  (entget e))))))
;(setq BB_A  (rtos (float (* (fix (+ (/ (* OLCEK b_value) SAYI) 0.5)) SAYI)) 2 0))
;(setq BB_B  (rtos (float (* (fix (+ (/ (* OLCEK s_value) SAYI) 0.5)) SAYI)) 2 0))
;(setq BB_C  (rtos (float (* (fix (+ (/ (* OLCEK h_value) SAYI) 0.5)) SAYI)) 2 0))
;(setq BB_R  (rtos (float (* (fix (+ (/ (* OLCEK r_value) SAYI) 0.5)) SAYI)) 2 0))
(princ)
)
;-------------------------------------------------------------------------------
(defun donati_tani_1 (P1 P2 / )
   (setq boy_1 (float (* (fix (+ (/ (* oran (distance P1 P2)) SAYI) 0.5)) SAYI)))
   (setq poz "X")
   (setq tip "00")
   (setq BB_A (rtos boy_1 2 0))
   (setq BB_B "0")
   (setq BB_C "0")
   (setq BB_D "0")
   (setq BB_E "0")
   (setq BB_F "0")
   (setq BB_R "0")
   (setq boy (b_h TIP BB_A BB_B BB_C BB_D BB_E BB_F (atof BB_R) 10))
)
;-------------------------------------------------------------------------------
(defun donati_tani_2 (P1 P2 P3 / )
       (if (> (distance P1 P2) (distance P2 P3)) (progn (setq P4 P1) (setq P1 P3) (setq P3 P4)))
       (setq PP1 (LIST (- (CAR P1) (CAR P2)) (- (CADR P1) (CADR P2)) 0.0 ))
       (setq PP2 (LIST 0.0 0.0 0.0))
       (setq PP3 (LIST (- (CAR P3) (CAR P2)) (- (CADR P3) (CADR P2)) 0.0 ))
       (if (= (CAR PP3) 0) (setq teta (* 0.5 pi)) (setq teta (* -1 (atan (/ (CADR PP3) (CAR PP3))))))
       (setq PP1 (koordinat_dondur PP1 teta))
       (setq PP3 (koordinat_dondur PP3 teta))
       (if (< (CAR PP3) 0 )
         (progn
          (setq PP1 (koordinat_dondur PP1 pi))
          (setq PP2 (koordinat_dondur PP2 pi))
          (setq PP3 (koordinat_dondur PP3 pi))
         )
       )
       (if (< (CADR PP1) 0 )
          (setq PP1 (LIST (CAR PP1) (* -1 (CADR PP1)) 0.0 ))
       )
        (setq alfa1 (fix (+ 0.5 (/ (* 180 (angle PP2 PP1)) pi))))
        (setq boy_1 (float (* (fix (+ (/ (* oran (distance PP1 PP2)) SAYI) 0.5)) SAYI)))
        (setq boy_2 (float (* (fix (+ (/ (* oran (distance PP2 PP3)) SAYI) 0.5)) SAYI)))
          (setq poz "X")
          (cond
             ((< alfa1 90)
               (progn
                (setq boy_3 (float (* (fix (+ (/ (* oran (abs (* boy_1 (Sin (angle PP2 PP1))))) SAYI) 0.5)) SAYI)))
                (if (= boy_1 boy_3)
                   (progn
                    (setq tip "11")
                    (setq BB_A (rtos boy_1 2 0))
                    (setq BB_B (rtos boy_2 2 0))
                    (setq BB_C "0")
                   )
                   (progn
                    (setq tip "14")
                    (setq BB_A (rtos boy_1 2 0))
                    (setq BB_B (rtos boy_3 2 0))
                    (setq BB_C (rtos boy_2 2 0))
                   )
                )
                (setq BB_D "0")
                (setq BB_E "0")
                (setq BB_F "0")
                (setq BB_R "0")
                (setq boy (b_h TIP BB_A BB_B BB_C BB_D BB_E BB_F (atof BB_R) 10))
               )
             )
             ((= alfa1 90)
               (progn
                (setq tip "11")
                (setq BB_A (rtos boy_1 2 0))
                (setq BB_B (rtos boy_2 2 0))
                (setq BB_C "0")
                (setq BB_D "0")
                (setq BB_E "0")
                (setq BB_F "0")
                (setq BB_R "0")
                (setq boy (b_h TIP BB_A BB_B BB_C BB_D BB_E BB_F (atof BB_R) 10))
               )
             )
             ((> alfa1 90)
               (progn
                (setq boy_3 (float (* (fix (+ (/ (* oran (abs (* boy_1 (Sin (angle PP2 PP1))))) SAYI) 0.5)) SAYI)))
                (if (= boy_1 boy_3)
                   (progn
                    (setq tip "11")
                    (setq BB_A (rtos boy_1 2 0))
                    (setq BB_B (rtos boy_2 2 0))
                    (setq BB_C "0")
                   )
                   (progn
                    (setq tip "15")
                    (setq BB_A (rtos boy_1 2 0))
                    (setq BB_B (rtos boy_3 2 0))
                    (setq BB_C (rtos boy_2 2 0))
                   )
                )
                (setq BB_D "0")
                (setq BB_E "0")
                (setq BB_F "0")
                (setq BB_R "0")
                (setq boy (b_h TIP BB_A BB_B BB_C BB_D BB_E BB_F (atof BB_R) 10))
               )
             )
             ( T (princ "\n Donatı tanınamadı. Tespit başarısız...")
                (setq tip  "99")
                (setq boy "L=0")
                (setq BB_A "0")
                (setq BB_B "0")
                (setq BB_C "0")
                (setq BB_D "0")
                (setq BB_E "0")
                (setq BB_F "0")
                (setq BB_R "0")
             )
          )
)
;-------------------------------------------------------------------------------
(defun donati_tani_3 (P1 P2 P3 P4 / )
       (setq PP1 (LIST (- (CAR P1) (CAR P2)) (- (CADR P1) (CADR P2)) 0.0 ))
       (setq PP2 (LIST 0.0 0.0 0.0))
       (setq PP3 (LIST (- (CAR P3) (CAR P2)) (- (CADR P3) (CADR P2)) 0.0 ))
       (setq PP4 (LIST (- (CAR P4) (CAR P2)) (- (CADR P4) (CADR P2)) 0.0 ))
       (if (= (CAR PP3) 0) (setq teta (* 0.5 pi)) (setq teta (* -1 (atan (/ (CADR PP3) (CAR PP3))))))
       (setq PP1 (koordinat_dondur PP1 teta))
       (setq PP3 (koordinat_dondur PP3 teta))
       (setq PP4 (koordinat_dondur PP4 teta))
       (if (< (CAR PP3) 0 )
         (progn
          (setq PP1 (koordinat_dondur PP1 pi))
          (setq PP2 (koordinat_dondur PP2 pi))
          (setq PP3 (koordinat_dondur PP3 pi))
          (setq PP4 (koordinat_dondur PP4 pi))
         )
       )
       (if (< (CADR PP1) 0 )
         (progn
          (setq PP1 (LIST (CAR PP1) (* -1 (CADR PP1)) 0.0 ))
          (setq PP4 (LIST (CAR PP4) (* -1 (CADR PP4)) 0.0 ))
         )
       )
        (setq alfa1 (fix (+ 0.5 (/ (* 180 (angle PP2 PP1)) pi))))
        (setq alfa2 (fix (+ 0.5 (/ (* 180 (angle PP3 PP4)) pi))))
        (setq boy_1 (float (* (fix (+ (/ (* oran (distance PP1 PP2)) SAYI) 0.5)) SAYI)))
        (setq boy_2 (float (* (fix (+ (/ (* oran (distance PP2 PP3)) SAYI) 0.5)) SAYI)))
        (setq boy_3 (float (* (fix (+ (/ (* oran (distance PP3 PP4)) SAYI) 0.5)) SAYI)))
        ;(princ "\n Alfa 1 : ") (princ alfa1)
        ;(princ "\n Alfa 2 : ") (princ alfa2)
        ;(princ "\n Boy  1 : ") (princ boy_1)
        ;(princ "\n Boy  2 : ") (princ boy_2)
        ;(princ "\n Boy  3 : ") (princ boy_3)
          (setq poz "X")
          (cond
             ((and (< alfa1 90) (> alfa2  90) (< alfa2 180))
               (progn
                  (setq boy_4 (float (* (fix (+ (/ (* oran (abs (* boy_1 (Sin (angle PP2 PP1))))) SAYI) 0.5)) SAYI)))
                  (setq boy_5 (float (* (fix (+ (/ (* oran (abs (* boy_3 (Sin (angle PP3 PP4))))) SAYI) 0.5)) SAYI)))
                  (if (and (= boy_1 boy_4) (= boy_3 boy_5))
                       (progn
                        (setq tip  "21")
                        (setq BB_A (rtos boy_1 2 0))
                        (setq BB_B (rtos boy_2 2 0))
                        (setq BB_C (rtos boy_3 2 0))
                        (setq BB_D "0")
                        (setq BB_E "0")
                       )
                       (progn
                        (setq tip  "17")
                        (setq BB_A (rtos boy_1 2 0))
                        (setq BB_B (rtos boy_3 2 0))
                        (setq BB_C (rtos boy_4 2 0))
                        (setq BB_D (rtos boy_5 2 0))
                        (setq BB_E (rtos boy_2 2 0))
                       )
                   )
                (setq BB_F "0")
                (setq BB_R "0")
                (setq boy (b_h TIP BB_A BB_B BB_C BB_D BB_E BB_F (atof BB_R) 10))
               )
             )
             ((and (< alfa1 90) (= alfa2  90)              )
               (progn
                  (setq boy_4 (float (* (fix (+ (/ (* oran (abs (* boy_1 (Sin (angle PP2 PP1))))) SAYI) 0.5)) SAYI)))
                  (if (= boy_1 boy_4)
                       (progn
                        (setq tip  "21")
                        (setq BB_A (rtos boy_1 2 0))
                        (setq BB_B (rtos boy_2 2 0))
                        (setq BB_C (rtos boy_3 2 0))
                        (setq BB_D "0")
                       )
                       (if (> boy_2 boy_3)
                         (progn
                          (setq tip  "18")
                          (setq BB_A (rtos boy_1 2 0))
                          (setq BB_B (rtos boy_2 2 0))
                          (setq BB_C (rtos boy_3 2 0))
                          (setq BB_D (rtos boy_4 2 0))
                         )
                         (progn
                          (setq tip  "40")
                          (setq BB_A (rtos boy_2 2 0))
                          (setq BB_B (rtos boy_3 2 0))
                          (setq BB_C (rtos boy_1 2 0))
                          (setq BB_D "0")
                         )
                       )
                   )
                (setq BB_E "0")
                (setq BB_F "0")
                (setq BB_R "0")
                (setq boy (b_h TIP BB_A BB_B BB_C BB_D BB_E BB_F (atof BB_R) 10))
               )
             )
             ((and (= alfa1 90) (> alfa2  90) (< alfa2 180))
               (progn
                  (setq boy_4 (float (* (fix (+ (/ (* oran (abs (* boy_3 (Sin (angle PP3 PP4))))) SAYI) 0.5)) SAYI)))
                  (if (= boy_3 boy_4)
                       (progn
                        (setq tip  "21")
                        (setq BB_A (rtos boy_3 2 0))
                        (setq BB_B (rtos boy_2 2 0))
                        (setq BB_C (rtos boy_1 2 0))
                        (setq BB_D "0")
                       )
                       (if (> boy_2 boy_1)
                         (progn
                          (setq tip  "18")
                          (setq BB_A (rtos boy_3 2 0))
                          (setq BB_B (rtos boy_2 2 0))
                          (setq BB_C (rtos boy_1 2 0))
                          (setq BB_D (rtos boy_4 2 0))
                         )
                         (progn
                          (setq tip  "40")
                          (setq BB_A (rtos boy_2 2 0))
                          (setq BB_B (rtos boy_1 2 0))
                          (setq BB_C (rtos boy_3 2 0))
                          (setq BB_D "0")
                         )
                       )
                   )
                (setq BB_E "0")
                (setq BB_F "0")
                (setq BB_R "0")
                (setq boy (b_h TIP BB_A BB_B BB_C BB_D BB_E BB_F (atof BB_R) 10))
               )
             )
             ((and (< alfa1 90) (< alfa2  90)              )
               (progn
                (if (and (= alfa1 alfa2) (or (> boy_1 boy_2) (> boy_3 boy_2)))
                 (progn
                  (setq tip "29")
                  (setq BB_A (rtos boy_1 2 0))
                  (setq BB_B (rtos boy_2 2 0))
                  (setq BB_C (rtos boy_3 2 0))
                  (setq BB_D (rtos (float (* (fix (+ (/ (* oran (abs (* boy_2 (Sin (angle PP2 PP1))))) SAYI) 0.5)) SAYI)) 2 0))
                  (setq BB_E "0")
                  (setq BB_F "0")
                  (setq BB_R "0")
                  (setq boy (b_h TIP BB_A BB_B BB_C BB_D BB_E BB_F (atof BB_R) 10))
                 )
                 (progn
                  (setq boy_4 (float (* (fix (+ (/ (* oran (abs (* boy_1 (Sin (angle PP2 PP1))))) SAYI) 0.5)) SAYI)))
                  (setq boy_5 (float (* (fix (+ (/ (* oran (abs (* boy_3 (Sin (angle PP3 PP4))))) SAYI) 0.5)) SAYI)))
                  (if (and (= boy_1 boy_4) (= boy_3 boy_5))
                       (progn
                        (setq tip  "21")
                        (setq BB_A (rtos boy_1 2 0))
                        (setq BB_B (rtos boy_2 2 0))
                        (setq BB_C (rtos boy_3 2 0))
                        (setq BB_D "0")
                        (setq BB_E "0")
                       )
                       (progn
                        (setq tip  "19")
                        (setq BB_A (rtos boy_1 2 0))
                        (setq BB_B (rtos boy_3 2 0))
                        (setq BB_C (rtos boy_4 2 0))
                        (setq BB_D (rtos boy_5 2 0))
                        (setq BB_E (rtos boy_2 2 0))
                       )
                   )
                  (setq BB_F "0")
                  (setq BB_R "0")
                  (setq boy (b_h TIP BB_A BB_B BB_C BB_D BB_E BB_F (atof BB_R) 10))
                 )
                )
               )
             )
             ((and (> alfa1 90) (> alfa2  90) (< alfa2 180))
               (progn
                (if (and (= alfa1 alfa2) (or (> boy_1 boy_2) (> boy_3 boy_2)))
                 (progn
                  (setq tip "29")
                  (setq BB_A (rtos boy_3 2 0))
                  (setq BB_B (rtos boy_2 2 0))
                  (setq BB_C (rtos boy_1 2 0))
                  (setq BB_D (rtos (float (* (fix (+ (/ (* oran (abs (* boy_2 (Sin (angle PP3 PP4))))) SAYI) 0.5)) SAYI)) 2 0))
                  (setq BB_E "0")
                  (setq BB_F "0")
                  (setq BB_R "0")
                  (setq boy (b_h TIP BB_A BB_B BB_C BB_D BB_E BB_F (atof BB_R) 10))
                 )
                 (progn
                  (setq boy_4 (float (* (fix (+ (/ (* oran (abs (* boy_3 (Sin (angle PP3 PP4))))) SAYI) 0.5)) SAYI)))
                  (setq boy_5 (float (* (fix (+ (/ (* oran (abs (* boy_1 (Sin (angle PP2 PP1))))) SAYI) 0.5)) SAYI)))
                  (if (and (= boy_3 boy_4) (= boy_1 boy_5))
                       (progn
                        (setq tip  "21")
                        (setq BB_A (rtos boy_3 2 0))
                        (setq BB_B (rtos boy_2 2 0))
                        (setq BB_C (rtos boy_1 2 0))
                        (setq BB_D "0")
                        (setq BB_E "0")
                       )
                       (progn
                        (setq tip  "19")
                        (setq BB_A (rtos boy_3 2 0))
                        (setq BB_B (rtos boy_1 2 0))
                        (setq BB_C (rtos boy_4 2 0))
                        (setq BB_D (rtos boy_5 2 0))
                        (setq BB_E (rtos boy_2 2 0))
                       )
                   )
                  (setq BB_F "0")
                  (setq BB_R "0")
                  (setq boy (b_h TIP BB_A BB_B BB_C BB_D BB_E BB_F (atof BB_R) 10))
                 )
                )
               )
             )
             ((and (= alfa1 90) (= alfa2  90)              )
               (progn
                (if (or (> boy_1 boy_2) (> boy_3 boy_2))
                 (setq tip "38")
                 (setq tip "21")
                )
                (setq BB_A (rtos (min boy_1 boy_3) 2 0))
                (setq BB_B (rtos boy_2 2 0))
                (setq BB_C (rtos (max boy_1 boy_3) 2 0))
                (setq BB_D "0")
                (setq BB_E "0")
                (setq BB_F "0")
                (setq BB_R "0")
                (setq boy (b_h TIP BB_A BB_B BB_C BB_D BB_E BB_F (atof BB_R) 10))
               )
             )
             ((and (= alfa1 90) (= alfa2 270)              )
               (progn
                (setq tip "23")
                (setq BB_A (rtos (min boy_1 boy_3) 2 0))
                (setq BB_B (rtos boy_2 2 0))
                (setq BB_C (rtos (max boy_1 boy_3) 2 0))
                (setq BB_D "0")
                (setq BB_E "0")
                (setq BB_F "0")
                (setq BB_R "0")
                (setq boy (b_h TIP BB_A BB_B BB_C BB_D BB_E BB_F (atof BB_R) 10))
               )
             )
             ((and (> alfa1 90) (< alfa2  90)              )
               (progn
                  (setq boy_4 (float (* (fix (+ (/ (* oran (abs (* boy_1 (Sin (angle PP2 PP1))))) SAYI) 0.5)) SAYI)))
                  (setq boy_5 (float (* (fix (+ (/ (* oran (abs (* boy_3 (Sin (angle PP3 PP4))))) SAYI) 0.5)) SAYI)))
                  (if (and (= boy_1 boy_4) (= boy_3 boy_5))
                       (progn
                        (setq tip  "21")
                        (setq BB_A (rtos boy_1 2 0))
                        (setq BB_B (rtos boy_2 2 0))
                        (setq BB_C (rtos boy_3 2 0))
                        (setq BB_D "0")
                        (setq BB_E "0")
                       )
                       (progn
                         (if (or (> boy_1 boy_2) (> boy_3 boy_2))
                           (progn
                            (setq tip  "24")
                            (setq BB_A (rtos (max boy_1 boy_3) 2 0))
                            (setq BB_B (rtos boy_2 2 0))
                            (setq BB_C (rtos (min boy_1 boy_3) 2 0))
                            (setq BB_D (rtos (float (* (fix (+ (/ (* oran (abs (* boy_2 (Sin (if (> boy_1 boy_3) (angle PP2 PP1) (angle PP3 PP4)))))) SAYI) 0.5)) SAYI)) 2 0))
                            (setq BB_E "0")
                           )
                           (progn
                            (setq tip  "25")
                            (setq BB_A (rtos boy_1 2 0))
                            (setq BB_B (rtos boy_3 2 0))
                            (setq BB_C (rtos boy_4 2 0))
                            (setq BB_D (rtos boy_5 2 0))
                            (setq BB_E (rtos boy_2 2 0))
                           )
                         )
                       )
                   )
                (setq BB_F "0")
                (setq BB_R "0")
                (setq boy (b_h TIP BB_A BB_B BB_C BB_D BB_E BB_F (atof BB_R) 10))
               )
             )
             ((and (= alfa1 90) (< alfa2  90)              )
               (progn
                  (setq boy_4 (float (* (fix (+ (/ (* oran (abs (* boy_3 (Sin (angle PP3 PP4))))) SAYI) 0.5)) SAYI)))
                  (if (= boy_3 boy_4)
                       (progn
                        (setq tip  "21")
                        (setq BB_A (rtos boy_3 2 0))
                        (setq BB_B (rtos boy_2 2 0))
                        (setq BB_C (rtos boy_1 2 0))
                        (setq BB_D "0")
                       )
                       (progn
                        (setq tip  "27")
                        (setq BB_A (rtos boy_3 2 0))
                        (setq BB_B (rtos boy_2 2 0))
                        (setq BB_C (rtos boy_1 2 0))
                        (setq BB_D (rtos boy_4 2 0))
                       )
                   )
                (setq BB_E "0")
                (setq BB_F "0")
                (setq BB_R "0")
                (setq boy (b_h TIP BB_A BB_B BB_C BB_D BB_E BB_F (atof BB_R) 10))
               )
             )
             ((and (> alfa1 90) (= alfa2  90)              )
               (progn
                  (setq boy_4 (float (* (fix (+ (/ (* oran (abs (* boy_1 (Sin (angle PP2 PP1))))) SAYI) 0.5)) SAYI)))
                  (if (= boy_1 boy_4)
                       (progn
                        (setq tip  "21")
                        (setq BB_A (rtos boy_1 2 0))
                        (setq BB_B (rtos boy_2 2 0))
                        (setq BB_C (rtos boy_3 2 0))
                        (setq BB_D "0")
                       )
                       (progn
                        (setq tip  "27")
                        (setq BB_A (rtos boy_1 2 0))
                        (setq BB_B (rtos boy_2 2 0))
                        (setq BB_C (rtos boy_3 2 0))
                        (setq BB_D (rtos boy_4 2 0))
                       )
                   )
                (setq BB_E "0")
                (setq BB_F "0")
                (setq BB_R "0")
                (setq boy (b_h TIP BB_A BB_B BB_C BB_D BB_E BB_F (atof BB_R) 10))
               )
             )
             ((and (= alfa1 90) (> alfa2 270) (< alfa2 360))
               (progn
                (setq tip "28")
                (setq BB_A (rtos boy_3 2 0))
                (setq BB_B (rtos boy_2 2 0))
                (setq BB_C (rtos boy_1 2 0))
                (setq BB_D (rtos (float (* (fix (+ (/ (* oran (abs (* boy_3 (Sin (angle PP3 PP4))))) SAYI) 0.5)) SAYI)) 2 0))
                (setq BB_E "0")
                (setq BB_F "0")
                (setq BB_R "0")
                (setq boy (b_h TIP BB_A BB_B BB_C BB_D BB_E BB_F (atof BB_R) 10))
               )
             )
             ((and (> alfa1 90) (= alfa2 270)              )
               (progn
                (setq tip "28")
                (setq BB_A (rtos boy_1 2 0))
                (setq BB_B (rtos boy_2 2 0))
                (setq BB_C (rtos boy_3 2 0))
                (setq BB_D (rtos (float (* (fix (+ (/ (* oran (abs (* boy_1 (Sin (angle PP2 PP1))))) SAYI) 0.5)) SAYI)) 2 0))
                (setq BB_E "0")
                (setq BB_F "0")
                (setq BB_R "0")
                (setq boy (b_h TIP BB_A BB_B BB_C BB_D BB_E BB_F (atof BB_R) 10))
               )
             )
             ((and (> alfa1 90) (> alfa2 270) (< alfa2 360))
               (progn
                 (if (or (> boy_1 boy_2) (> boy_3 boy_2))
                   (progn
                     (setq tip "26")
                     (setq BB_A (rtos (max boy_1 boy_3) 2 0))
                     (setq BB_B (rtos      boy_2        2 0))
                     (setq BB_C (rtos (min boy_1 boy_3) 2 0))
                     (setq BB_D (rtos (float (* (fix (+ (/ (* oran (abs (* boy_2 (Sin (angle PP3 PP4))))) SAYI) 0.5)) SAYI)) 2 0))
                     (setq BB_E "0")
                   )
                   (progn
                     (setq tip "45")
                     (setq BB_A (rtos boy_1 2 0))
                     (setq BB_B (rtos boy_3 2 0))
                     (setq BB_C (rtos (float (* (fix (+ (/ (* oran (abs (* boy_1 (Sin (angle PP2 PP1))))) SAYI) 0.5)) SAYI)) 2 0))
                     (setq BB_D (rtos (float (* (fix (+ (/ (* oran (abs (* boy_3 (Sin (angle PP3 PP4))))) SAYI) 0.5)) SAYI)) 2 0))
                     (setq BB_E (rtos boy_2 2 0))
                   )
                 )
                     (setq BB_F "0")
                     (setq BB_R "0")

                (setq boy (b_h TIP BB_A BB_B BB_C BB_D BB_E BB_F (atof BB_R) 10))
               )
             )
             ((and (> alfa1 90) (> alfa2 180) (< alfa2 270))
               (progn
                (setq tip "55")
                (setq BB_A (rtos boy_1 2 0))
                (setq BB_B (rtos boy_3 2 0))
                (setq BB_C (rtos (float (* (fix (+ (/ (* oran (abs (* boy_1 (Sin (angle PP2 PP1))))) SAYI) 0.5)) SAYI)) 2 0))
                (setq BB_D (rtos (float (* (fix (+ (/ (* oran (abs (* boy_3 (Sin (angle PP3 PP4))))) SAYI) 0.5)) SAYI)) 2 0))
                (setq BB_E (rtos boy_2 2 0))
                (setq BB_F "0")
                (setq BB_R "0")
                (setq boy (b_h TIP BB_A BB_B BB_C BB_D BB_E BB_F (atof BB_R) 10))
               )
             )
             ((and (< alfa1 90) (> alfa2 270) (< alfa2 360))
               (progn
                (setq tip "55")
                (setq BB_A (rtos boy_3 2 0))
                (setq BB_B (rtos boy_1 2 0))
                (setq BB_C (rtos (float (* (fix (+ (/ (* oran (abs (* boy_3 (Sin (angle PP3 PP4))))) SAYI) 0.5)) SAYI)) 2 0))
                (setq BB_D (rtos (float (* (fix (+ (/ (* oran (abs (* boy_1 (Sin (angle PP2 PP1))))) SAYI) 0.5)) SAYI)) 2 0))
                (setq BB_E (rtos boy_2 2 0))
                (setq BB_F "0")
                (setq BB_R "0")
                (setq boy (b_h TIP BB_A BB_B BB_C BB_D BB_E BB_F (atof BB_R) 10))
               )
             )
             ( T (princ "\n Donatı tanınamadı. Tespit başarısız...")
                (setq tip  "99")
                (setq boy "L=0")
                (setq BB_A "0")
                (setq BB_B "0")
                (setq BB_C "0")
                (setq BB_D "0")
                (setq BB_E "0")
                (setq BB_F "0")
                (setq BB_R "0")
             )
          )
)
;-------------------------------------------------------------------------------
(defun donati_tani_4 (P1 P2 P3 P4 P5 / )
       (setq boy_2 (float (* (fix (+ (/ (* oran (distance P2 P3)) SAYI) 0.5)) SAYI)))
       (setq boy_3 (float (* (fix (+ (/ (* oran (distance P3 P4)) SAYI) 0.5)) SAYI)))
       (if (> boy_3 boy_2) (progn (setq P6 P1) (SETQ P1 P5) (SETQ P5 P6) (setq P6 P2) (SETQ P2 P4) (SETQ P4 P6)))
       (setq PP1 (LIST (- (CAR P1) (CAR P2)) (- (CADR P1) (CADR P2)) 0.0 ))
       (setq PP2 (LIST (- (CAR P2) (CAR P2)) (- (CADR P2) (CADR P2)) 0.0 ))
       (setq PP3 (LIST (- (CAR P3) (CAR P2)) (- (CADR P3) (CADR P2)) 0.0 ))
       (setq PP4 (LIST (- (CAR P4) (CAR P2)) (- (CADR P4) (CADR P2)) 0.0 ))
       (setq PP5 (LIST (- (CAR P5) (CAR P2)) (- (CADR P5) (CADR P2)) 0.0 ))
       (if (= (CAR PP3) 0) (setq teta (* 0.5 pi)) (setq teta (* -1 (atan (/ (CADR PP3) (CAR PP3))))))
       (setq PP1 (koordinat_dondur PP1 teta))
       (setq PP3 (koordinat_dondur PP3 teta))
       (setq PP4 (koordinat_dondur PP4 teta))
       (setq PP5 (koordinat_dondur PP5 teta))
       (if (< (CAR PP3) 0 )
         (progn
          (setq PP1 (koordinat_dondur PP1 pi))
          (setq PP3 (koordinat_dondur PP3 pi))
          (setq PP4 (koordinat_dondur PP4 pi))
          (setq PP5 (koordinat_dondur PP5 pi))
         )
       )
       (if (< (CADR PP1) 0 )
         (progn
          (setq PP1 (LIST (CAR PP1) (* -1 (CADR PP1)) 0.0 ))
          (setq PP4 (LIST (CAR PP4) (* -1 (CADR PP4)) 0.0 ))
          (setq PP5 (LIST (CAR PP5) (* -1 (CADR PP5)) 0.0 ))
         )
       )
        (setq boy_1 (float (* (fix (+ (/ (* oran (distance PP1 PP2)) SAYI) 0.5)) SAYI)))
        (setq boy_2 (float (* (fix (+ (/ (* oran (distance PP2 PP3)) SAYI) 0.5)) SAYI)))
        (setq boy_3 (float (* (fix (+ (/ (* oran (distance PP3 PP4)) SAYI) 0.5)) SAYI)))
        (setq boy_4 (float (* (fix (+ (/ (* oran (distance PP4 PP5)) SAYI) 0.5)) SAYI)))
        (setq alfa1 (fix (+ 0.5 (/ (* 180 (angle PP2 PP1)) pi))))
        (setq alfa2 (fix (+ 0.5 (/ (* 180 (angle PP3 PP4)) pi))))
        (setq alfa3 (fix (+ 0.5 (/ (* 180 (angle PP4 PP5)) pi))))
        (if (= alfa1 360) (setq alfa1 0))
        (if (= alfa2 360) (setq alfa2 0))
        (if (= alfa3 360) (setq alfa3 0))
        (setq poz "X")
        ;(princ "\n Alfa 1 : ") (princ alfa1)
        ;(princ "\n Alfa 2 : ") (princ alfa2)
        ;(princ "\n Alfa 3 : ") (princ alfa3)
        ;(COMMAND "PLINE" PP1 PP2 PP3 PP4 PP5 "" )
          (cond
             ((and (> alfa1 90) (< alfa2  90) (= (abs (- alfa2 alfa3)) 90))
               (progn
                (setq tip "30")
                (setq BB_A (rtos boy_1 2 0))
                (setq BB_B (rtos boy_2 2 0))
                (setq BB_C (rtos boy_3 2 0))
                (setq BB_D (rtos (float (* (fix (+ (/ (* oran (abs (* boy_2 (Sin (angle PP2 PP1))))) SAYI) 0.5)) SAYI)) 2 0))
                (setq BB_E (rtos boy_4 2 0))
                (setq BB_F "0")
                (setq BB_R "0")
                (setq boy (b_h TIP BB_A BB_B BB_C BB_D BB_E BB_F (atof BB_R) 10))
               )
             )
             ((and (= alfa1 90) (< alfa2  90) (= alfa3 90))
               (progn
                (setq tip "30")
                (setq BB_A (rtos boy_4 2 0))
                (setq BB_B (rtos boy_3 2 0))
                (setq BB_C (rtos boy_2 2 0))
                (setq BB_D (rtos (float (* (fix (+ (/ (* oran (abs (* boy_3 (Cos (angle PP3 PP4))))) SAYI) 0.5)) SAYI)) 2 0))
                (setq BB_E (rtos boy_1 2 0))
                (setq BB_F "0")
                (setq BB_R "0")
                (setq boy (b_h TIP BB_A BB_B BB_C BB_D BB_E BB_F (atof BB_R) 10))
               )
             )
             ((and (= alfa1 90) (= alfa2  90) (= alfa3 180))
               (progn
                (setq tip "31")
                (setq BB_A (rtos boy_4 2 0))
                (setq BB_B (rtos boy_3 2 0))
                (setq BB_C (rtos boy_2 2 0))
                (setq BB_D (rtos boy_1 2 0))
                (setq BB_E "0")
                (setq BB_F "0")
                (setq BB_R "0")
                (setq boy (b_h TIP BB_A BB_B BB_C BB_D BB_E BB_F (atof BB_R) 10))
               )
             )
             ((and (< alfa1 90) (= alfa2  90) (= alfa3 180))
               (progn
                (setq tip "53")
                (setq BB_A (rtos boy_4 2 0))
                (setq BB_B (rtos boy_3 2 0))
                (setq BB_C (rtos boy_2 2 0))
                (setq BB_D (rtos boy_1 2 0))
                (setq BB_E "0")
                (setq BB_F "0")
                (setq BB_R "0")
                (setq boy (b_h TIP BB_A BB_B BB_C BB_D BB_E BB_F (atof BB_R) 10))
               )
             )
             ((and (= alfa1 90) (= alfa2  90) (> alfa3 90) (< alfa3 180))
               (progn
                (setq tip "61")
                (setq BB_A (rtos boy_1 2 0))
                (setq BB_B (rtos boy_2 2 0))
                (setq BB_C (rtos boy_3 2 0))
                (setq BB_D (rtos boy_4 2 0))
                (setq BB_E "0")
                (setq BB_F (rtos (float (* (fix (+ (/ (* oran (abs (* boy_4 (Sin (angle PP4 PP5))))) SAYI) 0.5)) SAYI)) 2 0))
                (setq BB_R "0")
                (setq boy (b_h TIP BB_A BB_B BB_C BB_D BB_E BB_F (atof BB_R) 10))
               )
             )
             ((and (= alfa1 90) (= alfa2 270) (= alfa3 180))
               (progn
                (setq tip "32")
                (setq BB_A (rtos boy_1 2 0))
                (setq BB_B (rtos boy_2 2 0))
                (setq BB_C (rtos boy_3 2 0))
                (setq BB_D (rtos boy_4 2 0))
                (setq BB_E "0")
                (setq BB_F "0")
                (setq BB_R "0")
                (setq boy (b_h TIP BB_A BB_B BB_C BB_D BB_E BB_F (atof BB_R) 10))
               )
             )
             ((and (> alfa1 90) (< alfa1 180) (= alfa2 90) (= alfa3 180))
               (progn
                (setq tip "36")
                (setq BB_A (rtos boy_1 2 0))
                (setq BB_B (rtos boy_2 2 0))
                (setq BB_C (rtos boy_3 2 0))
                (setq BB_D (rtos boy_4 2 0))
                (setq BB_E (rtos (float (* (fix (+ (/ (* oran (abs (* boy_1 (Sin (angle PP2 PP1))))) SAYI) 0.5)) SAYI)) 2 0))
                (setq BB_F "0")
                (setq BB_R "0")
                (setq boy (b_h TIP BB_A BB_B BB_C BB_D BB_E BB_F (atof BB_R) 10))
               )
             )
             ((and (= alfa1 90) (< alfa2 90) (= alfa3 0))
               (progn
                (setq tip "54")
                (setq BB_A (rtos boy_1 2 0))
                (setq BB_B (rtos boy_2 2 0))
                (setq BB_C (rtos boy_3 2 0))
                (setq BB_D (rtos boy_4 2 0))
                (setq BB_E (rtos (float (* (fix (+ (/ (* oran (abs (* boy_3 (Sin (angle PP3 PP4))))) SAYI) 0.5)) SAYI)) 2 0))
                (setq BB_F "0")
                (setq BB_R "0")
                (setq boy (b_h TIP BB_A BB_B BB_C BB_D BB_E BB_F (atof BB_R) 10))
               )
             )
             ((and (= (abs (- alfa1 alfa2)) 180) (= (abs (- alfa2 alfa3)) 90))
               (progn
                (setq tip "34")
                (setq BB_A (rtos boy_1 2 0))
                (setq BB_B (rtos boy_2 2 0))
                (setq BB_C (rtos boy_3 2 0))
                (setq BB_D (rtos (float (* (fix (+ (/ (* oran (abs (* boy_2 (Sin (angle PP2 PP1))))) SAYI) 0.5)) SAYI)) 2 0))
                (setq BB_E (rtos boy_4 2 0))
                (setq BB_F "0")
                (setq BB_R "0")
                (setq boy (b_h TIP BB_A BB_B BB_C BB_D BB_E BB_F (atof BB_R) 10))
               )
             )
             ((and (= alfa1 90) (> alfa2 270) (< alfa2 360)  (= alfa3 0))
               (progn
                (setq tip "35")
                (setq BB_A (rtos boy_4 2 0))
                (setq BB_B (rtos boy_3 2 0))
                (setq BB_C (rtos boy_2 2 0))
                (setq BB_D (rtos (float (* (fix (+ (/ (* oran (abs (* boy_3 (Sin (angle PP3 PP4))))) SAYI) 0.5)) SAYI)) 2 0))
                (setq BB_E (rtos boy_1 2 0))
                (setq BB_F "0")
                (setq BB_R "0")
                (setq boy (b_h TIP BB_A BB_B BB_C BB_D BB_E BB_F (atof BB_R) 10))
               )
             )
             ((and (= (abs (- alfa1 alfa2)) 180) (= (abs (- alfa2 alfa3)) 270))
               (progn
                (setq tip "35")
                (setq BB_A (rtos boy_1 2 0))
                (setq BB_B (rtos boy_2 2 0))
                (setq BB_C (rtos boy_3 2 0))
                (setq BB_D (rtos (float (* (fix (+ (/ (* oran (abs (* boy_2 (Sin (angle PP2 PP1))))) SAYI) 0.5)) SAYI)) 2 0))
                (setq BB_E (rtos boy_4 2 0))
                (setq BB_F "0")
                (setq BB_R "0")
                (setq boy (b_h TIP BB_A BB_B BB_C BB_D BB_E BB_F (atof BB_R) 10))
               )
             )
             ((and (< alfa1 90) (= alfa2 90) (> alfa3 180) (< alfa3 270))
               (progn
                (setq tip "52")
                (setq BB_A (rtos boy_3 2 0))
                (setq BB_B (rtos boy_2 2 0))
                (setq BB_C (rtos boy_4 2 0))
                (setq BB_D (rtos boy_1 2 0))
                (setq BB_E "0")
                (setq BB_F "0")
                (setq BB_R "0")
                (setq boy (b_h TIP BB_A BB_B BB_C BB_D BB_E BB_F (atof BB_R) 10))
               )
             )
             ( T (princ "\n Donatı tanınamadı. Tespit başarısız...")
                (setq tip  "99")
                (setq boy "L=0")
                (setq BB_A "0")
                (setq BB_B "0")
                (setq BB_C "0")
                (setq BB_D "0")
                (setq BB_E "0")
                (setq BB_F "0")
                (setq BB_R "0")
             )
          )
)
;-------------------------------------------------------------------------------
(defun donati_tani_5 (P1 P2 P3 P4 P5 P6 / )
;       (setq boy_2 (float (* (fix (+ (/ (* oran (distance P2 P3)) SAYI) 0.5)) SAYI)))
;       (setq boy_3 (float (* (fix (+ (/ (* oran (distance P3 P4)) SAYI) 0.5)) SAYI)))
;       (if (> boy_3 boy_2) (progn (setq P6 P1) (SETQ P1 P5) (SETQ P5 P6) (setq P6 P2) (SETQ P2 P4) (SETQ P4 P6)))
       (setq PP1 (LIST (- (CAR P1) (CAR P3)) (- (CADR P1) (CADR P3)) 0.0 ))
       (setq PP2 (LIST (- (CAR P2) (CAR P3)) (- (CADR P2) (CADR P3)) 0.0 ))
       (setq PP3 (LIST (- (CAR P3) (CAR P3)) (- (CADR P3) (CADR P3)) 0.0 ))
       (setq PP4 (LIST (- (CAR P4) (CAR P3)) (- (CADR P4) (CADR P3)) 0.0 ))
       (setq PP5 (LIST (- (CAR P5) (CAR P3)) (- (CADR P5) (CADR P3)) 0.0 ))
       (setq PP6 (LIST (- (CAR P6) (CAR P3)) (- (CADR P6) (CADR P3)) 0.0 ))
       (if (= (CAR PP4) 0) (setq teta (* 0.5 pi)) (setq teta (* -1 (atan (/ (CADR PP4) (CAR PP4))))))
       (setq PP1 (koordinat_dondur PP1 teta))
       (setq PP2 (koordinat_dondur PP2 teta))
       (setq PP4 (koordinat_dondur PP4 teta))
       (setq PP5 (koordinat_dondur PP5 teta))
       (setq PP6 (koordinat_dondur PP6 teta))
       (if (< (CAR PP4) 0 )
         (progn
          (setq PP1 (koordinat_dondur PP1 pi))
          (setq PP2 (koordinat_dondur PP2 pi))
          (setq PP4 (koordinat_dondur PP4 pi))
          (setq PP5 (koordinat_dondur PP5 pi))
          (setq PP6 (koordinat_dondur PP6 pi))
         )
       )
       (if (< (CADR PP2) 0 )
         (progn
          (setq PP1 (LIST (CAR PP1) (* -1 (CADR PP1)) 0.0 ))
          (setq PP2 (LIST (CAR PP2) (* -1 (CADR PP2)) 0.0 ))
          (setq PP5 (LIST (CAR PP5) (* -1 (CADR PP5)) 0.0 ))
          (setq PP6 (LIST (CAR PP6) (* -1 (CADR PP6)) 0.0 ))
         )
       )
        (setq boy_1 (float (* (fix (+ (/ (* oran (distance PP1 PP2)) SAYI) 0.5)) SAYI)))
        (setq boy_2 (float (* (fix (+ (/ (* oran (distance PP2 PP3)) SAYI) 0.5)) SAYI)))
        (setq boy_3 (float (* (fix (+ (/ (* oran (distance PP3 PP4)) SAYI) 0.5)) SAYI)))
        (setq boy_4 (float (* (fix (+ (/ (* oran (distance PP4 PP5)) SAYI) 0.5)) SAYI)))
        (setq boy_5 (float (* (fix (+ (/ (* oran (distance PP5 PP6)) SAYI) 0.5)) SAYI)))
        (setq alfa1 (fix (+ 0.5 (/ (* 180 (angle PP2 PP1)) pi))))
        (setq alfa2 (fix (+ 0.5 (/ (* 180 (angle PP3 PP2)) pi))))
        (setq alfa3 (fix (+ 0.5 (/ (* 180 (angle PP4 PP5)) pi))))
        (setq alfa4 (fix (+ 0.5 (/ (* 180 (angle PP5 PP6)) pi))))
        (if (= alfa1 360) (setq alfa1 0))
        (if (= alfa2 360) (setq alfa2 0))
        (if (= alfa3 360) (setq alfa3 0))
        (if (= alfa4 360) (setq alfa4 0))
        (setq poz "X")
        ;(princ "\n Alfa 1 : ") (princ alfa1)
        ;(princ "\n Alfa 2 : ") (princ alfa2)
        ;(princ "\n Alfa 3 : ") (princ alfa3)
        ;(princ "\n Alfa 4 : ") (princ alfa4)
        ;(COMMAND "PLINE" PP1 PP2 PP3 PP4 PP5 PP6 "" )
          (cond
             ((and (= alfa1 alfa3) (= alfa2  alfa4) (= (abs (- alfa1 alfa2)) 90) (= (abs (- alfa3 alfa4)) 90))
               (progn
                (setq tip "20")
                (if (> boy_2 boy_4)
                   (progn
                    (setq BB_A (rtos boy_1 2 0))
                    (setq BB_B (rtos boy_2 2 0))
                    (setq BB_C (rtos boy_3 2 0))
                    (setq BB_D (rtos boy_4 2 0))
                    (setq BB_E (rtos boy_5 2 0))
                    (setq BB_F (rtos (float (* (fix (+ (/ (* oran (abs (* boy_3 (Sin (angle PP3 PP2))))) SAYI) 0.5)) SAYI)) 2 0))
                    (setq BB_R "0")
                   )
                   (progn
                    (setq BB_A (rtos boy_5 2 0))
                    (setq BB_B (rtos boy_4 2 0))
                    (setq BB_C (rtos boy_3 2 0))
                    (setq BB_D (rtos boy_2 2 0))
                    (setq BB_E (rtos boy_1 2 0))
                    (setq BB_F (rtos (float (* (fix (+ (/ (* oran (abs (* boy_3 (Sin (angle PP4 PP5))))) SAYI) 0.5)) SAYI)) 2 0))
                    (setq BB_R "0")
                   )
                 )
                (setq boy (b_h TIP BB_A BB_B BB_C BB_D BB_E BB_F (atof BB_R) 10))
               )
             )
             ((and (> alfa1 270) (= alfa2  90) (= alfa3 90) (> alfa4 180) (< alfa4 270))
               (progn
                (setq tip "39")
                (setq BB_A (rtos boy_2 2 0))
                (setq BB_B (rtos boy_3 2 0))
                (setq BB_C (rtos boy_4 2 0))
                (setq BB_D (rtos boy_1 2 0))
                (setq BB_E (rtos boy_5 2 0))
                (setq BB_F "0")
                (setq BB_R "0")
                (setq boy (b_h TIP BB_A BB_B BB_C BB_D BB_E BB_F (atof BB_R) 10))
               )
             )
             ((and (= alfa1 0) (= alfa2  90) (= alfa3 90) (= alfa4 180))
               (progn
                (setq tip "41")
                (setq BB_A (rtos boy_1 2 0))
                (setq BB_B (rtos boy_2 2 0))
                (setq BB_C (rtos boy_3 2 0))
                (setq BB_D (rtos boy_4 2 0))
                (setq BB_E (rtos boy_5 2 0))
                (setq BB_F "0")
                (setq BB_R "0")
                (setq boy (b_h TIP BB_A BB_B BB_C BB_D BB_E BB_F (atof BB_R) 10))
               )
             )
             ((and (= alfa1 180) (= alfa2  90) (= alfa3 90) (= alfa4 0))
               (progn
                (setq tip "44")
                (setq BB_A (rtos boy_1 2 0))
                (setq BB_B (rtos boy_2 2 0))
                (setq BB_C (rtos boy_3 2 0))
                (setq BB_D (rtos boy_4 2 0))
                (setq BB_E (rtos boy_5 2 0))
                (setq BB_F "0")
                (setq BB_R "0")
                (setq boy (b_h TIP BB_A BB_B BB_C BB_D BB_E BB_F (atof BB_R) 10))
               )
             )
             ((and (= alfa1 180) (> alfa2 90) (< alfa2 180) (< alfa3 90) (= alfa4 0) (= boy_2 boy_4))
               (progn
                (setq tip "46")
                (setq BB_A (rtos boy_1 2 0))
                (setq BB_B (rtos boy_2 2 0))
                (setq BB_C (rtos boy_3 2 0))
                (setq BB_D (rtos (float (* (fix (+ (/ (* oran (abs (* boy_2 (Sin (angle PP3 PP2))))) SAYI) 0.5)) SAYI)) 2 0))
                (setq BB_E (rtos boy_5 2 0))
                (setq BB_F "0")
                (setq BB_R "0")
                (setq boy (b_h TIP BB_A BB_B BB_C BB_D BB_E BB_F (atof BB_R) 10))
               )
             )
             ((and (= alfa1 0) (= alfa2 90) (< alfa3 90) (= alfa4 90))
               (progn
                (setq tip "59")
                (setq BB_A (rtos boy_1 2 0))
                (setq BB_B (rtos boy_2 2 0))
                (setq BB_C (rtos boy_3 2 0))
                (setq BB_D (rtos boy_4 2 0))
                (setq BB_E (rtos boy_5 2 0))
                (setq BB_F (rtos (float (* (fix (+ (/ (* oran (abs (* boy_4 (Cos (angle PP4 PP5))))) SAYI) 0.5)) SAYI)) 2 0))
                (setq BB_R "0")
                (setq boy (b_h TIP BB_A BB_B BB_C BB_D BB_E BB_F (atof BB_R) 10))
               )
             )
             ((and (= alfa1 90) (> alfa2 90) (< alfa2 180) (= alfa3 90) (= alfa4 180))
               (progn
                (setq tip "59")
                (setq BB_A (rtos boy_5 2 0))
                (setq BB_B (rtos boy_4 2 0))
                (setq BB_C (rtos boy_3 2 0))
                (setq BB_D (rtos boy_2 2 0))
                (setq BB_E (rtos boy_1 2 0))
                (setq BB_F (rtos (float (* (fix (+ (/ (* oran (abs (* boy_2 (Cos (angle PP3 PP2))))) SAYI) 0.5)) SAYI)) 2 0))
                (setq BB_R "0")
                (setq boy (b_h TIP BB_A BB_B BB_C BB_D BB_E BB_F (atof BB_R) 10))
               )
             )
             (    (and (= alfa1 180) (= alfa2 90) (< alfa3 90) (= alfa4 0))
               (progn
                (setq tip "62")
                (setq BB_A (rtos boy_1 2 0))
                (setq BB_B (rtos boy_2 2 0))
                (setq BB_C (rtos boy_3 2 0))
                (setq BB_D (rtos boy_4 2 0))
                (setq BB_E (rtos boy_5 2 0))
                (setq BB_F (rtos (float (* (fix (+ (/ (* oran (abs (* boy_4 (Sin (angle PP4 PP5))))) SAYI) 0.5)) SAYI)) 2 0))
                (setq BB_R "0")
                (setq boy (b_h TIP BB_A BB_B BB_C BB_D BB_E BB_F (atof BB_R) 10))
               )
             )
             (    (and (= alfa1 180) (> alfa2 90) (= alfa3 90) (= alfa4 0))
               (progn
                (setq tip "62")
                (setq BB_A (rtos boy_5 2 0))
                (setq BB_B (rtos boy_4 2 0))
                (setq BB_C (rtos boy_3 2 0))
                (setq BB_D (rtos boy_2 2 0))
                (setq BB_E (rtos boy_1 2 0))
                (setq BB_F (rtos (float (* (fix (+ (/ (* oran (abs (* boy_2 (Sin (angle PP2 PP3))))) SAYI) 0.5)) SAYI)) 2 0))
                (setq BB_R "0")
                (setq boy (b_h TIP BB_A BB_B BB_C BB_D BB_E BB_F (atof BB_R) 10))
               )
             )
             ( T (princ "\n Donatı tanınamadı. Tespit başarısız...")
                (setq tip  "99")
                (setq boy "L=0")
                (setq BB_A "0")
                (setq BB_B "0")
                (setq BB_C "0")
                (setq BB_D "0")
                (setq BB_E "0")
                (setq BB_F "0")
                (setq BB_R "0")
             )
          )
)
;-------------------------------------------------------------------------------
(defun donati_tani_6 (P1 P2 P3 P4 P5 P6 P7 / )
       (setq alfa1 (fix (+ 0.5 (/ (* 180 (angle P1 P2)) pi))))
       (setq alfa2 (fix (+ 0.5 (/ (* 180 (angle P5 P6)) pi))))
       (if (/= alfa1 alfa2) (progn
                                  (setq PG7 P1  )
                                  (setq PG6 P2  )
                                  (setq PG5 P3  )
                                  (setq PG4 P4  )
                                  (setq PG3 P5  )
                                  (setq PG2 P6  )
                                  (setq PG1 P7  )
                                  (setq P1  PG1 )
                                  (setq P2  PG2 )
                                  (setq P3  PG3 )
                                  (setq P4  PG4 )
                                  (setq P5  PG5 )
                                  (setq P6  PG6 )
                                  (setq P7  PG7 )
                                  )
       )
       (setq PP1 (LIST (- (CAR P1) (CAR P3)) (- (CADR P1) (CADR P3)) 0.0 ))
       (setq PP2 (LIST (- (CAR P2) (CAR P3)) (- (CADR P2) (CADR P3)) 0.0 ))
       (setq PP3 (LIST (- (CAR P3) (CAR P3)) (- (CADR P3) (CADR P3)) 0.0 ))
       (setq PP4 (LIST (- (CAR P4) (CAR P3)) (- (CADR P4) (CADR P3)) 0.0 ))
       (setq PP5 (LIST (- (CAR P5) (CAR P3)) (- (CADR P5) (CADR P3)) 0.0 ))
       (setq PP6 (LIST (- (CAR P6) (CAR P3)) (- (CADR P6) (CADR P3)) 0.0 ))
       (setq PP7 (LIST (- (CAR P7) (CAR P3)) (- (CADR P7) (CADR P3)) 0.0 ))

       (if (= (CAR PP4) 0) (setq teta (* 0.5 pi)) (setq teta (* -1 (atan (/ (CADR PP4) (CAR PP4))))))
       (setq PP1 (koordinat_dondur PP1 teta))
       (setq PP2 (koordinat_dondur PP2 teta))
       (setq PP4 (koordinat_dondur PP4 teta))
       (setq PP5 (koordinat_dondur PP5 teta))
       (setq PP6 (koordinat_dondur PP6 teta))
       (setq PP7 (koordinat_dondur PP7 teta))
       (if (< (CAR PP4) 0 )
         (progn
          (setq PP1 (koordinat_dondur PP1 pi))
          (setq PP2 (koordinat_dondur PP2 pi))
          (setq PP4 (koordinat_dondur PP4 pi))
          (setq PP5 (koordinat_dondur PP5 pi))
          (setq PP6 (koordinat_dondur PP6 pi))
          (setq PP7 (koordinat_dondur PP7 pi))
         )
       )
       (if (< (CADR PP2) 0 )
         (progn
          (setq PP1 (LIST (CAR PP1) (* -1 (CADR PP1)) 0.0 ))
          (setq PP2 (LIST (CAR PP2) (* -1 (CADR PP2)) 0.0 ))
          (setq PP5 (LIST (CAR PP5) (* -1 (CADR PP5)) 0.0 ))
          (setq PP6 (LIST (CAR PP6) (* -1 (CADR PP6)) 0.0 ))
          (setq PP7 (LIST (CAR PP7) (* -1 (CADR PP7)) 0.0 ))
         )
       )
        (setq boy_1 (float (* (fix (+ (/ (* oran (distance PP1 PP2)) SAYI) 0.5)) SAYI)))
        (setq boy_2 (float (* (fix (+ (/ (* oran (distance PP2 PP3)) SAYI) 0.5)) SAYI)))
        (setq boy_3 (float (* (fix (+ (/ (* oran (distance PP3 PP4)) SAYI) 0.5)) SAYI)))
        (setq boy_4 (float (* (fix (+ (/ (* oran (distance PP4 PP5)) SAYI) 0.5)) SAYI)))
        (setq boy_5 (float (* (fix (+ (/ (* oran (distance PP5 PP6)) SAYI) 0.5)) SAYI)))
        (setq boy_6 (float (* (fix (+ (/ (* oran (distance PP6 PP7)) SAYI) 0.5)) SAYI)))
        (setq alfa1 (fix (+ 0.5 (/ (* 180 (angle PP2 PP1)) pi))))
        (setq alfa2 (fix (+ 0.5 (/ (* 180 (angle PP3 PP2)) pi))))
        (setq alfa3 (fix (+ 0.5 (/ (* 180 (angle PP4 PP5)) pi))))
        (setq alfa4 (fix (+ 0.5 (/ (* 180 (angle PP5 PP6)) pi))))
        (setq alfa5 (fix (+ 0.5 (/ (* 180 (angle PP6 PP7)) pi))))
        (if (= alfa1 360) (setq alfa1 0))
        (if (= alfa2 360) (setq alfa2 0))
        (if (= alfa3 360) (setq alfa3 0))
        (if (= alfa4 360) (setq alfa4 0))
        (if (= alfa5 360) (setq alfa5 0))
        (setq poz "X")
        ;(princ "\n Alfa 1 : ") (princ alfa1)
        ;(princ "\n Alfa 2 : ") (princ alfa2)
        ;(princ "\n Alfa 3 : ") (princ alfa3)
        ;(princ "\n Alfa 4 : ") (princ alfa4)
        ;(princ "\n Alfa 5 : ") (princ alfa5)
        ;(COMMAND "PLINE" PP1 PP2 PP3 PP4 PP5 PP6 PP7 "" )
          (cond
             ((and (= alfa1 180) (> alfa2 90) (< alfa2 180) (< alfa3 90) (= alfa4 0) (= alfa5 270) (= boy_2 boy_4) (= (fix (distance PP6 PP7)) (fix (* (distance PP3 PP2) (Sin (angle PP3 PP2))))))
               (progn
                (setq tip "49")
                (setq BB_A (rtos boy_1 2 0))
                (setq BB_B (rtos boy_2 2 0))
                (setq BB_C (rtos boy_3 2 0))
                (setq BB_D (rtos boy_6 2 0))
                (setq BB_E (rtos boy_5 2 0))
                (setq BB_F "0")
                (setq BB_R "0")
                (setq boy (b_h TIP BB_A BB_B BB_C BB_D BB_E BB_F (atof BB_R) 10))
               )
             )
             ((and (= alfa1 180) (> alfa2 90) (< alfa2 180) (< alfa3 90) (= alfa4 0) (= alfa5 270) (= boy_2 boy_4) (/= (fix (distance PP6 PP7)) (fix (* (distance PP3 PP2) (Sin (angle PP3 PP2))))))
               (progn
                (setq tip "65")
                (setq BB_A (rtos boy_1 2 0))
                (setq BB_B (rtos boy_2 2 0))
                (setq BB_C (rtos boy_3 2 0))
                (setq BB_D (rtos boy_6 2 0))
                (setq BB_E (rtos boy_5 2 0))
                (setq BB_F (rtos (float (* (fix (+ (/ (* oran (abs (* boy_2 (Sin (angle PP3 PP2))))) SAYI) 0.5)) SAYI)) 2 0))
                (setq BB_R "0")
                (setq boy (b_h TIP BB_A BB_B BB_C BB_D BB_E BB_F (atof BB_R) 10))
               )
             )
             ( T (princ "\n Donatı tanınamadı. Tespit başarısız...")
                (setq tip  "99")
                (setq boy "L=0")
                (setq BB_A "0")
                (setq BB_B "0")
                (setq BB_C "0")
                (setq BB_D "0")
                (setq BB_E "0")
                (setq BB_F "0")
                (setq BB_R "0")
             )
          )
)

;-------------------------------------------------------------------------------
(defun donati_tani_7 (P1 P2 P3 P4 P5 P6 P7 P8 / )
       (setq PP1 (LIST (- (CAR P1) (CAR P4)) (- (CADR P1) (CADR P4)) 0.0 ))
       (setq PP2 (LIST (- (CAR P2) (CAR P4)) (- (CADR P2) (CADR P4)) 0.0 ))
       (setq PP3 (LIST (- (CAR P3) (CAR P4)) (- (CADR P3) (CADR P4)) 0.0 ))
       (setq PP4 (LIST (- (CAR P4) (CAR P4)) (- (CADR P4) (CADR P4)) 0.0 ))
       (setq PP5 (LIST (- (CAR P5) (CAR P4)) (- (CADR P5) (CADR P4)) 0.0 ))
       (setq PP6 (LIST (- (CAR P6) (CAR P4)) (- (CADR P6) (CADR P4)) 0.0 ))
       (setq PP7 (LIST (- (CAR P7) (CAR P4)) (- (CADR P7) (CADR P4)) 0.0 ))
       (setq PP8 (LIST (- (CAR P8) (CAR P4)) (- (CADR P8) (CADR P4)) 0.0 ))
       (if (= (CAR PP5) 0) (setq teta (* 0.5 pi)) (setq teta (* -1 (atan (/ (CADR PP5) (CAR PP5))))))
       (setq PP1 (koordinat_dondur PP1 teta))
       (setq PP2 (koordinat_dondur PP2 teta))
       (setq PP3 (koordinat_dondur PP3 teta))
       (setq PP5 (koordinat_dondur PP5 teta))
       (setq PP6 (koordinat_dondur PP6 teta))
       (setq PP7 (koordinat_dondur PP7 teta))
       (setq PP8 (koordinat_dondur PP8 teta))
       (if (< (CAR PP5) 0 )
         (progn
          (setq PP1 (koordinat_dondur PP1 pi))
          (setq PP2 (koordinat_dondur PP2 pi))
          (setq PP3 (koordinat_dondur PP3 pi))
          (setq PP5 (koordinat_dondur PP5 pi))
          (setq PP6 (koordinat_dondur PP6 pi))
          (setq PP7 (koordinat_dondur PP7 pi))
          (setq PP8 (koordinat_dondur PP8 pi))
         )
       )
       (if (< (CADR PP3) 0 )
         (progn
          (setq PP1 (LIST (CAR PP1) (* -1 (CADR PP1)) 0.0 ))
          (setq PP2 (LIST (CAR PP2) (* -1 (CADR PP2)) 0.0 ))
          (setq PP3 (LIST (CAR PP3) (* -1 (CADR PP3)) 0.0 ))
          (setq PP6 (LIST (CAR PP6) (* -1 (CADR PP6)) 0.0 ))
          (setq PP7 (LIST (CAR PP7) (* -1 (CADR PP7)) 0.0 ))
          (setq PP8 (LIST (CAR PP8) (* -1 (CADR PP8)) 0.0 ))
         )
       )
        (setq boy_1 (float (* (fix (+ (/ (* oran (distance PP1 PP2)) SAYI) 0.5)) SAYI)))
        (setq boy_2 (float (* (fix (+ (/ (* oran (distance PP2 PP3)) SAYI) 0.5)) SAYI)))
        (setq boy_3 (float (* (fix (+ (/ (* oran (distance PP3 PP4)) SAYI) 0.5)) SAYI)))
        (setq boy_4 (float (* (fix (+ (/ (* oran (distance PP4 PP5)) SAYI) 0.5)) SAYI)))
        (setq boy_5 (float (* (fix (+ (/ (* oran (distance PP5 PP6)) SAYI) 0.5)) SAYI)))
        (setq boy_6 (float (* (fix (+ (/ (* oran (distance PP6 PP7)) SAYI) 0.5)) SAYI)))
        (setq boy_7 (float (* (fix (+ (/ (* oran (distance PP7 PP8)) SAYI) 0.5)) SAYI)))
        (setq alfa1 (fix (+ 0.5 (/ (* 180 (angle PP2 PP1)) pi))))
        (setq alfa2 (fix (+ 0.5 (/ (* 180 (angle PP3 PP2)) pi))))
        (setq alfa3 (fix (+ 0.5 (/ (* 180 (angle PP4 PP3)) pi))))
        (setq alfa4 (fix (+ 0.5 (/ (* 180 (angle PP5 PP6)) pi))))
        (setq alfa5 (fix (+ 0.5 (/ (* 180 (angle PP6 PP7)) pi))))
        (setq alfa6 (fix (+ 0.5 (/ (* 180 (angle PP7 PP8)) pi))))
        (if (= alfa1 360) (setq alfa1 0))
        (if (= alfa2 360) (setq alfa2 0))
        (if (= alfa3 360) (setq alfa3 0))
        (if (= alfa4 360) (setq alfa4 0))
        (if (= alfa5 360) (setq alfa5 0))
        (if (= alfa6 360) (setq alfa6 0))
        (setq poz "X")
        ;(princ "\n Alfa 1 : ") (princ alfa1)
        ;(princ "\n Alfa 2 : ") (princ alfa2)
        ;(princ "\n Alfa 3 : ") (princ alfa3)
        ;(princ "\n Alfa 4 : ") (princ alfa4)
        ;(princ "\n Alfa 5 : ") (princ alfa5)
        ;(princ "\n Alfa 6 : ") (princ alfa6)
        ;(princ "\n Boy  1 : ") (princ boy_1)
        ;(princ "\n Boy  2 : ") (princ boy_2)
        ;(princ "\n Boy  3 : ") (princ boy_3)
        ;(princ "\n Boy  4 : ") (princ boy_4)
        ;(princ "\n Boy  5 : ") (princ boy_5)
        ;(princ "\n Boy  6 : ") (princ boy_6)
        ;(princ "\n Boy  7 : ") (princ boy_7)
        ;(COMMAND "PLINE" PP1 PP2 PP3 PP4 PP5 PP6 PP7 PP8 "" )
          (cond
             ((and (= alfa1 270) (= alfa2 180) (< alfa3 180) (> alfa3 90) (< alfa4 90) (= alfa5 0)  (= alfa6 270) (= boy_1 boy_7) (= boy_3 boy_5) (equal (fix (distance PP1 PP2)) (fix (* (distance PP3 PP4) (abs (Sin (angle PP3 PP4))))) 1 ))
               (progn
                (setq tip "48")
                (setq BB_A (rtos boy_2 2 0))
                (setq BB_B (rtos boy_3 2 0))
                (setq BB_C (rtos boy_4 2 0))
                (setq BB_D (rtos boy_1 2 0))
                (setq BB_E (rtos boy_6 2 0))
                (setq BB_F "0")
                (setq BB_R "0")
                (setq boy (b_h TIP BB_A BB_B BB_C BB_D BB_E BB_F (atof BB_R) 10))
               )
             )
             ( T (princ "\n Donatı tanınamadı. Tespit başarısız...")
                (setq tip  "99")
                (setq boy "L=0")
                (setq BB_A "0")
                (setq BB_B "0")
                (setq BB_C "0")
                (setq BB_D "0")
                (setq BB_E "0")
                (setq BB_F "0")
                (setq BB_R "0")
             )
          )
)
;-------------------------------------------------------------------------------
;-------------------------------------------------------------------------------
;-------------------------------------------------------------------------------
(defun donati_tani_key_action ( /
                                  P1 P2 P3 P4 P5 P6 P7 P8 P9
                                  PP1 PP2 PP3 PP4 PP5 PP6 PP7 PP8 PP9
                                  PG1 PG2 PG3 PG4 PG5 PG6 PG7 PG8 PG9
                                  P1A P1B P2A P2B P3A P3B
                                  teta
                                  alfa1 alfa2 alfa3 alfa4 alfa5 alfa6
                                  boy_1 boy_2 boy_3 boy_4 boy_5 boy_6 boy_7
                              )
(vl-load-com)
(SETQ SAYI 10)
(setq arckont 0)
(setq oran (GETVAR "DIMLFAC"))
(princ "\n Boy bilgileri çizgilerden alınacak. Donatı çizgilerini seçiniz. Lütfen...")
;
(setq B (ssget (list (cons -4  "<OR") (cons 0 "LINE") (cons 0 "LWPOLYLINE") (cons 0 "ARC") (cons -4  "OR>") )))
(if (= (cdr (assoc 8 (entget (ssname B 0)))) "5A") (progn (adet_al_key_action_a (ssname B 0)) (setq B nil)))
(if (/= B nil)
(progn
;
(if (and (= (sslength B) 1) (= (cdr (assoc 0 (entget (ssname B 0)))) "LWPOLYLINE"))
 (progn
  (setq bb (entget (ssname B 0)))
  (setq k 0 PtList nil H_List nil)
  (repeat (length bb)
   (setq bb_en (nth k bb))
   (if (= (car bb_en) 10)        (setq PtList (append PtList (list (cdr bb_en)))) )
   (if (= (car bb_en) 42) (progn (setq H_List (append H_List (list (cdr bb_en)))) (setq arckont (+ arckont (cdr bb_en)))))
    (setq k (1+ k))
  )
  (if (= (CDR (ASSOC 70 BB)) 1 )
   (progn
    (setq PtList (cons (nth (1- (length PtList)) PtList) PtList ))
    (setq H_List (cons (nth (1- (length H_List)) H_List) H_List ))
   )
  )
  (setq npt (length PtList))
  (princ "\n Npt : ") (princ npt) (princ " - Eğrisel : ") (princ arckont)
;-------------------------------------------------------------------------------
;- LWPolyLine tipi elemanlardan donatı tanıma bölümü ---------------------------
;-------------------------------------------------------------------------------
  (if (= arckont 0)
   (cond
     (
       (= npt 2)
       (progn
         (setq P1 (nth 0 PtList))
         (setq P2 (nth 1 PtList))
         (donati_tani_1 P1 P2)
       )
     )
     (
       (= npt 3)
       (progn
         (setq P1 (nth 0 PtList))
         (setq P2 (nth 1 PtList))
         (setq P3 (nth 2 PtList))
         (donati_tani_2 P1 P2 P3)
       )
     )
     (
       (= npt 4)
       (progn
         (setq P1 (nth 0 PtList))
         (setq P2 (nth 1 PtList))
         (setq P3 (nth 2 PtList))
         (setq P4 (nth 3 PtList))
         (donati_tani_3 P1 P2 P3 P4)
       )
     )
     (
       (= npt 5)
       (progn
         (setq P1 (nth 0 PtList))
         (setq P2 (nth 1 PtList))
         (setq P3 (nth 2 PtList))
         (setq P4 (nth 3 PtList))
         (setq P5 (nth 4 PtList))
         (donati_tani_4 P1 P2 P3 P4 P5)
       )
     )
     (
       (= npt 6)
       (progn
         (setq P1 (nth 0 PtList))
         (setq P2 (nth 1 PtList))
         (setq P3 (nth 2 PtList))
         (setq P4 (nth 3 PtList))
         (setq P5 (nth 4 PtList))
         (setq P6 (nth 5 PtList))
         (donati_tani_5 P1 P2 P3 P4 P5 P6)
       )
     )
     (
       (= npt 7)
       (progn
         (setq P1 (nth 0 PtList))
         (setq P2 (nth 1 PtList))
         (setq P3 (nth 2 PtList))
         (setq P4 (nth 3 PtList))
         (setq P5 (nth 4 PtList))
         (setq P6 (nth 5 PtList))
         (setq P7 (nth 6 PtList))
         (donati_tani_6 P1 P2 P3 P4 P5 P6 P7)
       )
     )
     (
       (= npt 8)
       (progn
         (setq P1 (nth 0 PtList))
         (setq P2 (nth 1 PtList))
         (setq P3 (nth 2 PtList))
         (setq P4 (nth 3 PtList))
         (setq P5 (nth 4 PtList))
         (setq P6 (nth 5 PtList))
         (setq P7 (nth 6 PtList))
         (setq P8 (nth 7 PtList))
         (donati_tani_7 P1 P2 P3 P4 P5 P6 P7 P8)
       )
     )
     (
      T
       (progn
        (princ "\n 7 ten fazla kolu olan pline seçtiniz. Tespit başarısız...")
        (setq tip  "99")
        (setq boy "L=0")
        (setq BB_A "0")
        (setq BB_B "0")
        (setq BB_C "0")
        (setq BB_D "0")
        (setq BB_E "0")
        (setq BB_F "0")
        (setq BB_R "0")
       )
     )
   )
;Burdan sonra arc içeren Pline lar için donatı tanıma yapılmaktadır.
   (cond
     (
       (= npt 2)
       (progn
;-------------------------------------------------------------------------------
; Tek parçalı aslında bir ARC olan elemanlar.
;-------------------------------------------------------------------------------
         (setq P1    (nth 0 PtList))
         (setq P2    (nth 1 PtList))
         (setq ARC_H (nth 0 H_List))
         (pline_icin_arc_coz P1 P2 ARC_H)
         (setq poz  "X")
         (setq tip  "67")
         (setq BB_A  (rtos (float (* (fix (+ (/ (* oran b_value) SAYI) 0.5)) SAYI)) 2 0))
         (setq BB_B  (rtos (float (* (fix (+ (/ (* oran s_value) SAYI) 0.5)) SAYI)) 2 0))
         (setq BB_C  (rtos (float (* (fix (+ (/ (* oran h_value) SAYI) 0.5)) SAYI)) 2 0))
         (setq BB_D "0")
         (setq BB_E "0")
         (setq BB_F "0")
         (setq BB_R  (rtos (float (* (fix (+ (/ (* oran r_value) SAYI) 0.5)) SAYI)) 2 0))
         (setq boy (b_h TIP BB_A BB_B BB_C BB_D BB_E BB_F (atof BB_R) 10))
       )
     )
     (
       (and (= npt 3) (or (= (nth 0 H_List) 0) (= (nth 1 H_List) 0)))
       (progn
;-------------------------------------------------------------------------------
; İki paçalı bir ARC ve bir Line olan elemanlar.
;-------------------------------------------------------------------------------
         (if (/= (nth 0 H_List) 0)
          (progn
            (setq P1 (nth 0 PtList))
            (setq P2 (nth 1 PtList))
            (setq P3 (nth 2 PtList))
            (setq ARC_H1 (nth 0 H_List))
          )
          (progn
            (setq P1 (nth 2 PtList))
            (setq P2 (nth 1 PtList))
            (setq P3 (nth 0 PtList))
           (setq ARC_H1 (* -1 (nth 1 H_List)))
          )
         )
       (setq PP1 (LIST (- (CAR P1) (CAR P1)) (- (CADR P1) (CADR P1)) 0.0 ))
       (setq PP2 (LIST (- (CAR P2) (CAR P1)) (- (CADR P2) (CADR P1)) 0.0 ))
       (setq PP3 (LIST (- (CAR P3) (CAR P1)) (- (CADR P3) (CADR P1)) 0.0 ))
       (if (= (CAR PP2) 0) (setq teta (* 0.5 pi)) (setq teta (* -1 (atan (/ (CADR PP2) (CAR PP2))))))
       (setq PP2 (koordinat_dondur PP2 teta))
       (setq PP3 (koordinat_dondur PP3 teta))
       (if (< (CAR PP2) 0 )
         (progn
          (setq PP2 (koordinat_dondur PP2 pi))
          (setq PP3 (koordinat_dondur PP3 pi))
         )
       )
       (if (< (CADR PP3) 0 )
         (progn
          (setq PP3 (LIST (CAR PP3) (* -1 (CADR PP3)) 0.0 ))
          (setq ARC_H1 (* -1 ARC_H1))
         )
       )
        (setq boy_2 (float (* (fix (+ (/ (* oran (distance PP2 PP3)) SAYI) 0.5)) SAYI)))
        (setq alfa2 (fix (+ 0.5 (/ (* 180 (angle PP2 PP3)) pi))))
        (if (= alfa2 360) (setq alfa2 0))
;
        (pline_icin_arc_coz PP1 PP2 ARC_H1)
;
  (setq BB_A (rtos (float (* (fix (+ (/ (* oran (abs b_value)) SAYI) 0.5)) SAYI)) 2 0))
  (setq BB_B (rtos (float (* (fix (+ (/ (* oran (abs s_value)) SAYI) 0.5)) SAYI)) 2 0))
  (setq BB_C (rtos (float (* (fix (+ (/ (* oran (abs h_value)) SAYI) 0.5)) SAYI)) 2 0))
  (setq BB_D (rtos (float (* (fix (+ (/ (* oran boy_2)   SAYI) 0.5)) SAYI)) 2 0))
  (setq BB_E "0")
  (setq BB_F "0")
  (setq BB_R  (rtos (float (* (fix (+ (/ (* oran (abs r_value)) SAYI) 0.5)) SAYI)) 2 0))
   (cond
     ((and (> ARC_H1 0) (= alfa2 90)) (progn (setq tip  "68") (setq boy (b_h TIP BB_A BB_B BB_C BB_D BB_E BB_F (atof BB_R) 10))))
     ((and (< ARC_H1 0) (= alfa2 90)) (progn (setq tip  "69") (setq boy (b_h TIP BB_A BB_B BB_C BB_D BB_E BB_F (atof BB_R) 10))))
     ((and (> ARC_H1 0) (> alfa2 90)) (progn (setq tip  "78") (setq boy (b_h TIP BB_A BB_B BB_C BB_D BB_E BB_F (atof BB_R) 10))))
     ((and (< ARC_H1 0) (< alfa2 90)) (progn (setq tip  "79") (setq boy (b_h TIP BB_A BB_B BB_C BB_D BB_E BB_F (atof BB_R) 10))))
     ((and (> ARC_H1 0) (< alfa2 90)) (progn (setq tip  "82") (setq boy (b_h TIP BB_A BB_B BB_C BB_D BB_E BB_F (atof BB_R) 10))))
     ( T (progn
          (princ "\n Donatı tanınamadı. Tespit başarısız...")
          (setq tip  "99")
          (setq boy "L=0")
          (setq BB_A "0")
          (setq BB_B "0")
          (setq BB_C "0")
          (setq BB_D "0")
          (setq BB_E "0")
          (setq BB_F "0")
          (setq BB_R "0")
         )
     )
   )
   )
   )
     (
       (and (= npt 4) (= (nth 0 H_List) 0) (/= (nth 1 H_List) 0) (= (nth 2 H_List) 0))
       (progn
;-------------------------------------------------------------------------------
;-------------------------------------------------------------------------------
; Üç paçalı bir ARC ve iki Line olan elemanlar.                                ;
; ARC ortada ve iki yanda bir line olacak şekilde elemanlar.                   ;
;-------------------------------------------------------------------------------
;-------------------------------------------------------------------------------
       (setq P1     (nth 0 PtList))
       (setq P2     (nth 1 PtList))
       (setq P3     (nth 2 PtList))
       (setq P4     (nth 3 PtList))
       (setq ARC_H2 (nth 1 H_List))
       (setq poz  "X")
       (setq PP1 (LIST (- (CAR P1) (CAR P2)) (- (CADR P1) (CADR P2)) 0.0 ))
       (setq PP2 (LIST (- (CAR P2) (CAR P2)) (- (CADR P2) (CADR P2)) 0.0 ))
       (setq PP3 (LIST (- (CAR P3) (CAR P2)) (- (CADR P3) (CADR P2)) 0.0 ))
       (setq PP4 (LIST (- (CAR P4) (CAR P2)) (- (CADR P4) (CADR P2)) 0.0 ))
       (if (= (CAR PP3) 0) (setq teta (* 0.5 pi)) (setq teta (* -1 (atan (/ (CADR PP3) (CAR PP3))))))
       (setq PP1 (koordinat_dondur PP1 teta))
       (setq PP3 (koordinat_dondur PP3 teta))
       (setq PP4 (koordinat_dondur PP4 teta))
       (if (< (CAR PP3) 0 )
         (progn
          (setq PP1 (koordinat_dondur PP1 pi))
          (setq PP3 (koordinat_dondur PP3 pi))
          (setq PP4 (koordinat_dondur PP4 pi))
         )
       )
       (if (< (CADR PP1) 0 )
         (progn
          (setq PP1 (LIST (CAR PP1) (* -1 (CADR PP1)) 0.0 ))
          (setq PP4 (LIST (CAR PP4) (* -1 (CADR PP4)) 0.0 ))
          (setq ARC_H2 (* -1 ARC_H2))
         )
       )
        (setq boy_1 (float (* (fix (+ (/ (* oran (distance PP1 PP2)) SAYI) 0.5)) SAYI)))
        (setq boy_2 (float (* (fix (+ (/ (* oran (distance PP2 PP3)) SAYI) 0.5)) SAYI)))
        (setq boy_3 (float (* (fix (+ (/ (* oran (distance PP3 PP4)) SAYI) 0.5)) SAYI)))
        (setq alfa1 (fix (+ 0.5 (/ (* 180 (angle PP2 PP1)) pi))))
        (setq alfa2 (fix (+ 0.5 (/ (* 180 (angle PP3 PP4)) pi))))
        (if (= alfa1 360) (setq alfa1 0))
        (if (= alfa2 360) (setq alfa2 0))
;
        (pline_icin_arc_coz PP2 PP3 ARC_H2)
;
         (setq BB_A (rtos (float (* (fix (+ (/ (* oran (abs b_value)) SAYI) 0.5)) SAYI)) 2 0))
         (setq BB_B (rtos (float (* (fix (+ (/ (* oran (abs s_value)) SAYI) 0.5)) SAYI)) 2 0))
         (setq BB_C (rtos (float (* (fix (+ (/ (* oran (abs h_value)) SAYI) 0.5)) SAYI)) 2 0))
         (setq BB_D (rtos (float (* (fix (+ (/ (* oran      boy_1)    SAYI) 0.5)) SAYI)) 2 0))
         (setq BB_E (rtos (float (* (fix (+ (/ (* oran      boy_3)    SAYI) 0.5)) SAYI)) 2 0))
         (setq BB_F "0")
         (setq BB_R (rtos (float (* (fix (+ (/ (* oran (abs r_value)) SAYI) 0.5)) SAYI)) 2 0))
         (cond
           ((and (> ARC_H2 0) (= alfa1 90) (= alfa2 90)) (progn (setq tip "70") (setq boy (b_h TIP BB_A BB_B BB_C BB_D BB_E BB_F (atof BB_R) 10))))
           ((and (< ARC_H2 0) (= alfa1 90) (= alfa2 90)) (progn (setq tip "71") (setq boy (b_h TIP BB_A BB_B BB_C BB_D BB_E BB_F (atof BB_R) 10))))
           ((and (> ARC_H2 0) (< alfa1 90) (> alfa2 90)) (progn (setq tip "80") (setq boy (b_h TIP BB_A BB_B BB_C BB_D BB_E BB_F (atof BB_R) 10))))
           ((and (< ARC_H2 0) (> alfa1 90) (< alfa2 90)) (progn (setq tip "81") (setq boy (b_h TIP BB_A BB_B BB_C BB_D BB_E BB_F (atof BB_R) 10))))
           ((and (> ARC_H2 0) (> alfa1 90) (> alfa2 90)) (progn (setq tip "83") (setq boy (b_h TIP BB_A BB_B BB_C BB_D BB_E BB_F (atof BB_R) 10))))
           ((and (> ARC_H2 0) (< alfa1 90) (< alfa2 90)) (progn (setq tip "83") (setq boy (b_h TIP BB_A BB_B BB_C BB_D BB_E BB_F (atof BB_R) 10))))
           ( T (progn
                 (princ "\n Donatı tanınamadı. Tespit başarısız...")
                 (setq tip  "99")
                 (setq boy "L=0")
                 (setq BB_A "0")
                 (setq BB_B "0")
                 (setq BB_C "0")
                 (setq BB_D "0")
                 (setq BB_E "0")
                 (setq BB_F "0")
                 (setq BB_R "0")
               )
           )
         )
         (if (and (equal ARC_H2 1.000 0.001) (= alfa1 90) (= alfa2 90))
          (progn
            (setq tip  "13")
            (setq BB_A (rtos (float (* (fix (+ (/ (* oran (max boy_1 boy_3))    SAYI) 0.5)) SAYI)) 2 0))
            (setq BB_B (rtos (float (* (fix (+ (/ (* oran boy_2)    SAYI) 0.5)) SAYI)) 2 0))
            (setq BB_C (rtos (float (* (fix (+ (/ (* oran (min boy_1 boy_3))    SAYI) 0.5)) SAYI)) 2 0))
            (setq BB_D "0")
            (setq BB_E "0")
            (setq BB_F "0")
            (setq BB_R "0")
            (setq boy (b_h TIP BB_A BB_B BB_C BB_D BB_E BB_F (atof BB_R) 10))
          )
         )
         (if (and (equal ARC_H2 0.414 0.0009) (= alfa1 135) (= alfa2 45))
          (progn
            (setq tip  "12")
            (setq BB_A (rtos (float (* (fix (+ (/ (* oran (min boy_1 boy_3))    SAYI) 0.5)) SAYI)) 2 0))
            (setq BB_B (rtos (float (* (fix (+ (/ (* oran (max boy_1 boy_3))    SAYI) 0.5)) SAYI)) 2 0))
            (setq BB_C "0")
            (setq BB_D "0")
            (setq BB_E "0")
            (setq BB_F "0")
            (setq BB_R (rtos (float (* (fix (+ (/ (* oran (abs r_value)) SAYI) 0.5)) SAYI)) 2 0))
            (setq boy (b_h TIP BB_A BB_B BB_C BB_D BB_E BB_F (atof BB_R) 10))
          )
         )
       )
     )
     (
       (and (= npt 4) (= (nth 1 H_List) 0))
       (progn
       (setq P1     (nth 0 PtList))
       (setq P2     (nth 1 PtList))
       (setq P3     (nth 2 PtList))
       (setq P4     (nth 3 PtList))
       (setq poz  "X")
       (setq ARC_H1 (nth 0 H_List))
       (setq ARC_H3 (nth 2 H_List))
       (if (/= ARC_H3 0)
             (progn
               (setq P4     (nth 0 PtList))
               (setq P3     (nth 1 PtList))
               (setq P2     (nth 2 PtList))
               (setq P1     (nth 3 PtList))
               (setq ARC_H1 (nth 2 H_List))
             )
       )
       (setq PP1 (LIST (- (CAR P1) (CAR P1)) (- (CADR P1) (CADR P1)) 0.0 ))
       (setq PP2 (LIST (- (CAR P2) (CAR P1)) (- (CADR P2) (CADR P1)) 0.0 ))
       (setq PP3 (LIST (- (CAR P3) (CAR P1)) (- (CADR P3) (CADR P1)) 0.0 ))
       (setq PP4 (LIST (- (CAR P4) (CAR P1)) (- (CADR P4) (CADR P1)) 0.0 ))
       (if (= (CAR PP2) 0) (setq teta (* 0.5 pi)) (setq teta (* -1 (atan (/ (CADR PP2) (CAR PP2))))))
       (setq PP2 (koordinat_dondur PP2 teta))
       (setq PP3 (koordinat_dondur PP3 teta))
       (setq PP4 (koordinat_dondur PP4 teta))
       (if (< (CAR PP2) 0 )
         (progn
          (setq PP2 (koordinat_dondur PP2 pi))
          (setq PP3 (koordinat_dondur PP3 pi))
          (setq PP4 (koordinat_dondur PP4 pi))
         )
       )
       (if (< (CADR PP3) 0 )
         (progn
          (setq PP3 (LIST (CAR PP3) (* -1 (CADR PP3)) 0.0 ))
          (setq PP4 (LIST (CAR PP4) (* -1 (CADR PP4)) 0.0 ))
          (setq ARC_H1 (* -1 ARC_H1))
         )
       )
        (setq boy_1 (float (* (fix (+ (/ (* oran (distance PP1 PP2)) SAYI) 0.5)) SAYI)))
        (setq boy_2 (float (* (fix (+ (/ (* oran (distance PP2 PP3)) SAYI) 0.5)) SAYI)))
        (setq boy_3 (float (* (fix (+ (/ (* oran (distance PP3 PP4)) SAYI) 0.5)) SAYI)))
        (setq alfa1 (fix (+ 0.5 (/ (* 180 (angle PP2 PP3)) pi))))
        (setq alfa2 (fix (+ 0.5 (/ (* 180 (angle PP3 PP4)) pi))))
        (if (= alfa1 360) (setq alfa1 0))
        (if (= alfa2 360) (setq alfa2 0))
;
        (pline_icin_arc_coz PP1 PP2 ARC_H1)
;
        (cond
         ((and (< alfa1 90) (equal (- alfa2 alfa1 ) 90 15 ))
           (progn
            (setq tip  "72")
            (setq BB_A (rtos (float (* (fix (+ (/ (* oran (abs b_value)) SAYI) 0.5)) SAYI)) 2 0))
            (setq BB_B (rtos (float (* (fix (+ (/ (* oran (abs s_value)) SAYI) 0.5)) SAYI)) 2 0))
            (setq BB_C (rtos (float (* (fix (+ (/ (* oran (abs h_value)) SAYI) 0.5)) SAYI)) 2 0))
            (setq BB_D (rtos (float (* (fix (+ (/ (* oran      boy_2)    SAYI) 0.5)) SAYI)) 2 0))
            (setq BB_E (rtos (float (* (fix (+ (/ (* oran      boy_3)    SAYI) 0.5)) SAYI)) 2 0))
            (setq BB_F "0")
            (setq BB_R (rtos (float (* (fix (+ (/ (* oran (abs r_value)) SAYI) 0.5)) SAYI)) 2 0))
            (setq boy (b_h TIP BB_A BB_B BB_C BB_D BB_E BB_F (atof BB_R) 10))
            ;(command "pline" PP1 PP2 PP3 PP4 "" )
            ;(princ "\n Alfa 1 : ") (princ alfa1)
            ;(princ "\n Alfa 2 : ") (princ alfa2)
           )
         )
         (T
           (progn
            (princ "\n Donatı tanınamadı. Tespit başarısız...")
            (setq tip  "99")
            (setq boy "L=0")
            (setq BB_A "0")
            (setq BB_B "0")
            (setq BB_C "0")
            (setq BB_D "0")
            (setq BB_E "0")
            (setq BB_F "0")
            (setq BB_R "0")
           )
          )
        )
       )
     )
     (
       (and (= npt 5) (= (nth 0 H_List) 0) (or (and (/= (nth 1 H_List) 0) (= (nth 2 H_List) 0)) (and (= (nth 1 H_List) 0) (/= (nth 2 H_List) 0))) (= (nth 3 H_List) 0))
       (progn
;-------------------------------------------------------------------------------
;-------------------------------------------------------------------------------
; Üç paçalı bir ARC ve iki Line olan elemanlar.                                ;
; ARC ortada ve iki yanda bir line olacak şekilde elemanlar.                   ;
;-------------------------------------------------------------------------------
;-------------------------------------------------------------------------------
      (if  (= (nth 1 H_List) 0)
             (progn
              (setq P1     (nth 0 PtList))
              (setq P2     (nth 1 PtList))
              (setq P3     (nth 2 PtList))
              (setq P4     (nth 3 PtList))
              (setq P5     (nth 4 PtList))
              (setq ARC_H2 (nth 2 H_List))
             )
             (progn
              (setq P1     (nth 4 PtList))
              (setq P2     (nth 3 PtList))
              (setq P3     (nth 2 PtList))
              (setq P4     (nth 1 PtList))
              (setq P5     (nth 0 PtList))
              (setq ARC_H2 (nth 1 H_List))
             )
      )
       (setq poz  "X")
       (setq PP1 (LIST (- (CAR P1) (CAR P2)) (- (CADR P1) (CADR P2)) 0.0 ))
       (setq PP2 (LIST (- (CAR P2) (CAR P2)) (- (CADR P2) (CADR P2)) 0.0 ))
       (setq PP3 (LIST (- (CAR P3) (CAR P2)) (- (CADR P3) (CADR P2)) 0.0 ))
       (setq PP4 (LIST (- (CAR P4) (CAR P2)) (- (CADR P4) (CADR P2)) 0.0 ))
       (setq PP5 (LIST (- (CAR P5) (CAR P2)) (- (CADR P5) (CADR P2)) 0.0 ))

       (if (= (CAR PP3) 0) (setq teta (* 0.5 pi)) (setq teta (* -1 (atan (/ (CADR PP3) (CAR PP3))))))

       (setq PP1 (koordinat_dondur PP1 teta))
       (setq PP3 (koordinat_dondur PP3 teta))
       (setq PP4 (koordinat_dondur PP4 teta))
       (setq PP5 (koordinat_dondur PP5 teta))

       (if (< (CAR PP3) 0 )
         (progn
          (setq PP1 (koordinat_dondur PP1 pi))
          (setq PP3 (koordinat_dondur PP3 pi))
          (setq PP4 (koordinat_dondur PP4 pi))
          (setq PP5 (koordinat_dondur PP5 pi))
         )
       )
       (if (< (CADR PP1) 0 )
         (progn
          (setq PP1 (LIST (CAR PP1) (* -1 (CADR PP1)) 0.0 ))
          (setq PP4 (LIST (CAR PP4) (* -1 (CADR PP4)) 0.0 ))
          (setq PP5 (LIST (CAR PP5) (* -1 (CADR PP5)) 0.0 ))
          (setq ARC_H2 (* -1 ARC_H2))
         )
       )
        (setq boy_1 (float (* (fix (+ (/ (* oran (distance PP1 PP2)) SAYI) 0.5)) SAYI)))
        (setq boy_2 (float (* (fix (+ (/ (* oran (distance PP2 PP3)) SAYI) 0.5)) SAYI)))
        (setq boy_3 (float (* (fix (+ (/ (* oran (distance PP3 PP4)) SAYI) 0.5)) SAYI)))
        (setq boy_4 (float (* (fix (+ (/ (* oran (distance PP4 PP5)) SAYI) 0.5)) SAYI)))
        (setq alfa1 (fix (+ 0.5 (/ (* 180 (angle PP2 PP1)) pi))))
        (setq alfa2 (fix (+ 0.5 (/ (* 180 (angle PP3 PP4)) pi))))
        (setq alfa3 (fix (+ 0.5 (/ (* 180 (angle PP4 PP5)) pi))))
        (if (= alfa1 360) (setq alfa1 0))
        (if (= alfa2 360) (setq alfa2 0))
        (if (= alfa3 360) (setq alfa3 0))
;
        (pline_icin_arc_coz PP3 PP4 ARC_H2)
;
         (setq BB_A (rtos (float (* (fix (+ (/ (* oran (abs b_value)) SAYI) 0.5)) SAYI)) 2 0))
         (setq BB_B (rtos (float (* (fix (+ (/ (* oran (abs s_value)) SAYI) 0.5)) SAYI)) 2 0))
         (setq BB_C (rtos (float (* (fix (+ (/ (* oran (abs h_value)) SAYI) 0.5)) SAYI)) 2 0))
         (setq BB_D (rtos (float (* (fix (+ (/ (* oran      boy_1)    SAYI) 0.5)) SAYI)) 2 0))
         (setq BB_E (rtos (float (* (fix (+ (/ (* oran      boy_3)    SAYI) 0.5)) SAYI)) 2 0))
         (setq BB_F "0")
         (setq BB_R (rtos (float (* (fix (+ (/ (* oran (abs r_value)) SAYI) 0.5)) SAYI)) 2 0))
         (if (and (equal ARC_H2 1.000 0.001) (= alfa1 90) (= alfa2 90) (= alfa3 180))
          (progn
            (setq tip  "22")
            (setq BB_A (rtos boy_1 2 0))
            (setq BB_B (rtos boy_2 2 0))
            (setq BB_C (rtos boy_3 2 0))
            (setq BB_D (rtos boy_4 2 0))
            (setq BB_E "0")
            (setq BB_F "0")
            (setq BB_R "0")
            (setq boy (b_h TIP BB_A BB_B BB_C BB_D BB_E BB_F (atof BB_R) 10))
          )
         )
       )
     )
     (
      T
       (progn
         (princ "\n Donatı tanınamadı. Tespit başarısız...")
         (setq tip  "99")
         (setq boy "L=0")
         (setq BB_A "0")
         (setq BB_B "0")
         (setq BB_C "0")
         (setq BB_D "0")
         (setq BB_E "0")
         (setq BB_F "0")
         (setq BB_R "0")
       )
     )
   )
  )
 )
)
;-------------------------------------------------------------------------------
; Bir arc elemandan yay donatı tanımıma için -----------------------------------
;-------------------------------------------------------------------------------
(if (and (= (sslength B) 1) (= (cdr (assoc 0 (entget (ssname B 0)))) "ARC"))
 (progn
   (arc_coz (ssname B 0))
   (setq tip  "67")
   (setq BB_A  (rtos (float (* (fix (+ (/ (* oran b_value) SAYI) 0.5)) SAYI)) 2 0))
   (setq BB_B  (rtos (float (* (fix (+ (/ (* oran s_value) SAYI) 0.5)) SAYI)) 2 0))
   (setq BB_C  (rtos (float (* (fix (+ (/ (* oran h_value) SAYI) 0.5)) SAYI)) 2 0))
   (setq BB_D "0")
   (setq BB_E "0")
   (setq BB_F "0")
   (setq BB_R  (rtos (float (* (fix (+ (/ (* oran r_value) SAYI) 0.5)) SAYI)) 2 0))
   (setq boy (b_h TIP BB_A BB_B BB_C BB_D BB_E BB_F (atof BB_R) 10))
 )
)
;-------------------------------------------------------------------------------
; Bir line dan düz donatı tanımı için ------------------------------------------
;-------------------------------------------------------------------------------
(if (and (= (sslength B) 1) (= (cdr (assoc 0 (entget (ssname B 0)))) "LINE"))
 (progn
   (setq P1 (cdr (assoc 10 (entget (ssname B 0)))))
   (setq P2 (cdr (assoc 11 (entget (ssname B 0)))))
   (donati_tani_1 P1 P2)
 )
)
;-------------------------------------------------------------------------------
; İki line dan donatı tanıma ---------------------------------------------------
;-------------------------------------------------------------------------------
(if (and (= (sslength B) 2) (= (cdr (assoc 0 (entget (ssname B 0)))) "LINE")(= (cdr (assoc 0 (entget (ssname B 1)))) "LINE"))
 (progn
      (setq P1A (cdr (assoc 10 (entget (ssname B 0)))))
      (setq P1B (cdr (assoc 11 (entget (ssname B 0)))))
      (setq P2A (cdr (assoc 10 (entget (ssname B 1)))))
      (setq P2B (cdr (assoc 11 (entget (ssname B 1)))))
      (COND
       ((Equal P1A P2A 1)  (PROGN (SETQ P1 P1B) (SETQ P2 P1A) (SETQ P3 P2B)))
       ((Equal P1A P2B 1)  (PROGN (SETQ P1 P1B) (SETQ P2 P1A) (SETQ P3 P2A)))
       ((Equal P1B P2A 1)  (PROGN (SETQ P1 P1A) (SETQ P2 P1B) (SETQ P3 P2B)))
       ((Equal P1B P2B 1)  (PROGN (SETQ P1 P1A) (SETQ P2 P1B) (SETQ P3 P2A)))
      )
  (if (or (= P1 nil) (= P2 nil) (= P3 nil))
   (progn
    (princ "\n Eleman uç noktaları birleşmiyor. Tespit başarısız...")
    (setq poz "X")
    (setq tip  "99")
    (setq boy "L=0")
    (setq BB_A "0")
    (setq BB_B "0")
    (setq BB_C "0")
    (setq BB_D "0")
    (setq BB_E "0")
    (setq BB_F "0")
    (setq BB_R "0")
   )
  (donati_tani_2 P1 P2 P3 )
  )
 )
)
;-------------------------------------------------------------------------------
; Üç line dan donatı tanıma ---------------------------------------------------
;-------------------------------------------------------------------------------
(if (and (= (sslength B) 3) (= (cdr (assoc 0 (entget (ssname B 0)))) "LINE")(= (cdr (assoc 0 (entget (ssname B 1)))) "LINE")(= (cdr (assoc 0 (entget (ssname B 2)))) "LINE"))
 (progn
      (setq P1A (cdr (assoc 10 (entget (ssname B 0)))))
      (setq P1B (cdr (assoc 11 (entget (ssname B 0)))))
      (setq P2A (cdr (assoc 10 (entget (ssname B 1)))))
      (setq P2B (cdr (assoc 11 (entget (ssname B 1)))))
      (setq P3A (cdr (assoc 10 (entget (ssname B 2)))))
      (setq P3B (cdr (assoc 11 (entget (ssname B 2)))))
      (COND
       ((AND (Equal P1A P3A 1) (Equal P1B P2A 1)) (PROGN (SETQ P1 P3B) (SETQ P2 P1A) (SETQ P3 P1B) (SETQ P4 P2B)))
       ((AND (Equal P1A P3A 1) (Equal P1B P2B 1)) (PROGN (SETQ P1 P3B) (SETQ P2 P1A) (SETQ P3 P1B) (SETQ P4 P2A)))
       ((AND (Equal P1A P3B 1) (Equal P1B P2A 1)) (PROGN (SETQ P1 P3A) (SETQ P2 P1A) (SETQ P3 P1B) (SETQ P4 P2B)))
       ((AND (Equal P1A P3B 1) (Equal P1B P2B 1)) (PROGN (SETQ P1 P3A) (SETQ P2 P1A) (SETQ P3 P1B) (SETQ P4 P2A)))
       ((AND (Equal P1B P3A 1) (Equal P1A P2A 1)) (PROGN (SETQ P1 P3B) (SETQ P2 P1B) (SETQ P3 P1A) (SETQ P4 P2B)))
       ((AND (Equal P1B P3A 1) (Equal P1A P2B 1)) (PROGN (SETQ P1 P3B) (SETQ P2 P1B) (SETQ P3 P1A) (SETQ P4 P2A)))
       ((AND (Equal P1B P3B 1) (Equal P1A P2A 1)) (PROGN (SETQ P1 P3A) (SETQ P2 P1B) (SETQ P3 P1A) (SETQ P4 P2B)))
       ((AND (Equal P1B P3B 1) (Equal P1A P2B 1)) (PROGN (SETQ P1 P3A) (SETQ P2 P1B) (SETQ P3 P1A) (SETQ P4 P2A)))
       ((AND (Equal P2A P1A 1) (Equal P2B P3A 1)) (PROGN (SETQ P1 P1B) (SETQ P2 P2A) (SETQ P3 P2B) (SETQ P4 P3B)))
       ((AND (Equal P2A P1A 1) (Equal P2B P3B 1)) (PROGN (SETQ P1 P1B) (SETQ P2 P2A) (SETQ P3 P2B) (SETQ P4 P3A)))
       ((AND (Equal P2A P1B 1) (Equal P2B P3A 1)) (PROGN (SETQ P1 P1A) (SETQ P2 P2A) (SETQ P3 P2B) (SETQ P4 P3B)))
       ((AND (Equal P2A P1B 1) (Equal P2B P3B 1)) (PROGN (SETQ P1 P1A) (SETQ P2 P2A) (SETQ P3 P2B) (SETQ P4 P3A)))
       ((AND (Equal P2B P1A 1) (Equal P2A P3A 1)) (PROGN (SETQ P1 P1B) (SETQ P2 P2B) (SETQ P3 P2A) (SETQ P4 P3B)))
       ((AND (Equal P2B P1A 1) (Equal P2A P3B 1)) (PROGN (SETQ P1 P1B) (SETQ P2 P2B) (SETQ P3 P2A) (SETQ P4 P3A)))
       ((AND (Equal P2B P1B 1) (Equal P2A P3A 1)) (PROGN (SETQ P1 P1A) (SETQ P2 P2B) (SETQ P3 P2A) (SETQ P4 P3B)))
       ((AND (Equal P2B P1B 1) (Equal P2A P3B 1)) (PROGN (SETQ P1 P1A) (SETQ P2 P2B) (SETQ P3 P2A) (SETQ P4 P3A)))
       ((AND (Equal P3A P2A 1) (Equal P3B P1A 1)) (PROGN (SETQ P1 P2B) (SETQ P2 P3A) (SETQ P3 P3B) (SETQ P4 P1B)))
       ((AND (Equal P3A P2A 1) (Equal P3B P1B 1)) (PROGN (SETQ P1 P2B) (SETQ P2 P3A) (SETQ P3 P3B) (SETQ P4 P1A)))
       ((AND (Equal P3A P2B 1) (Equal P3B P1A 1)) (PROGN (SETQ P1 P2A) (SETQ P2 P3A) (SETQ P3 P3B) (SETQ P4 P1B)))
       ((AND (Equal P3A P2B 1) (Equal P3B P1B 1)) (PROGN (SETQ P1 P2A) (SETQ P2 P3A) (SETQ P3 P3B) (SETQ P4 P1A)))
       ((AND (Equal P3B P2A 1) (Equal P3A P1A 1)) (PROGN (SETQ P1 P2B) (SETQ P2 P3B) (SETQ P3 P3A) (SETQ P4 P1B)))
       ((AND (Equal P3B P2A 1) (Equal P3A P1B 1)) (PROGN (SETQ P1 P2B) (SETQ P2 P3B) (SETQ P3 P3A) (SETQ P4 P1A)))
       ((AND (Equal P3B P2B 1) (Equal P3A P1A 1)) (PROGN (SETQ P1 P2A) (SETQ P2 P3B) (SETQ P3 P3A) (SETQ P4 P1B)))
       ((AND (Equal P3B P2B 1) (Equal P3A P1B 1)) (PROGN (SETQ P1 P2A) (SETQ P2 P3B) (SETQ P3 P3A) (SETQ P4 P1A)))
      )
  (if (or (= P1 nil) (= P2 nil) (= P3 nil) (= P4 nil))
   (progn
    (princ "\n Elemanlar uç nontaları birleşmiyor. Tespit başarısız...")
    (setq poz "X")
    (setq tip  "99")
    (setq boy "L=0")
    (setq BB_A "0")
    (setq BB_B "0")
    (setq BB_C "0")
    (setq BB_D "0")
    (setq BB_E "0")
    (setq BB_F "0")
    (setq BB_R "0")
   )
   (donati_tani_3 P1 P2 P3 P4 )
  )
 )
) ; Üç parçalı donatıların tanınması işi sonu
;-------------------------------------------------------------------------------
;- Donatıların line lardan tanıması işi 3 elemandan sonra desteklenmemektedir. -
;- Üçten fazla eleman adeti için LWPolyLine olarak tanıması gereklidir.        -
;-------------------------------------------------------------------------------
(if (> (sslength B) 3)
  (progn
    (princ "\n 3 ten fazla çizgi seçtiniz. Tespit başarısız...")
    (setq tip  "99")
    (setq boy "L=0")
    (setq BB_A "0")
    (setq BB_B "0")
    (setq BB_C "0")
    (setq BB_D "0")
    (setq BB_E "0")
    (setq BB_F "0")
    (setq BB_R "0")
  )
)
)
(princ "\n Hiç eleman seçmediniz. Tespit başarısız...!")
)
(princ)
)
;-------------------------------------------------------------------------------
;-------------------------------------------------------------------------------
;-------------------------------------------------------------------------------
;-- Donatı tanıma kısmı sonu ---------------------------------------------------
;-------------------------------------------------------------------------------
;-------------------------------------------------------------------------------
;-------------------------------------------------------------------------------
(defun bukum_boyu_bagla (/)
(SetVar "CmdEcho" 0)
(if (= (getvar "FIELDDISPLAY") 0) (setvar "FIELDDISPLAY" 1)) ;1 arka tarafı beyaz gösterir
(setq line_en (car (entsel "\n Bukum boyu bilgisinin baglanacagi ( Line, Dimension, Circle, Text ) elemani secin ...  ")))
(if (/= line_en nil)
 (progn
  (setq Obj_vba_id (itoa (vlax-get-property (vlax-ename->vla-object line_en) 'ObjectId)))
  (IF (= "LINE"      (CDR (ASSOC 0 (entget line_en))))  (setq bag_text (strcat "%<\\AcObjProp Object(%<\\_ObjId " Obj_vba_id ">%).Length      \\f ""%lu2%pr0"">%" )))
  (IF (= "DIMENSION" (CDR (ASSOC 0 (entget line_en))))  (setq bag_text (strcat "%<\\AcObjProp Object(%<\\_ObjId " Obj_vba_id ">%).Measurement \\f ""%lu2%pr0"">%" )))
  (IF (= "CIRCLE"    (CDR (ASSOC 0 (entget line_en))))  (setq bag_text (strcat "%<\\AcObjProp Object(%<\\_ObjId " Obj_vba_id ">%).Diameter    \\f ""%lu2%pr0"">%" )))
  (IF (= "TEXT"      (CDR (ASSOC 0 (entget line_en))))  (setq bag_text (strcat "%<\\AcObjProp Object(%<\\_ObjId " Obj_vba_id ">%).TextString  \\f ""%tc1"">%"     )))
  (if (= tile_name "A_key") (progn (att_yaz en "A" bag_text ) (VL-CmdF "_.UpdateField" en "") (setq BB_A (a_oku en "A"))))
  (if (= tile_name "B_key") (progn (att_yaz en "B" bag_text ) (VL-CmdF "_.UpdateField" en "") (setq BB_B (a_oku en "B"))))
  (if (= tile_name "C_key") (progn (att_yaz en "C" bag_text ) (VL-CmdF "_.UpdateField" en "") (setq BB_C (a_oku en "C"))))
  (if (= tile_name "D_key") (progn (att_yaz en "D" bag_text ) (VL-CmdF "_.UpdateField" en "") (setq BB_D (a_oku en "D"))))
  (if (= tile_name "E_key") (progn (att_yaz en "E" bag_text ) (VL-CmdF "_.UpdateField" en "") (setq BB_E (a_oku en "E"))))
  (if (= tile_name "F_key") (progn (att_yaz en "F" bag_text ) (VL-CmdF "_.UpdateField" en "") (setq BB_F (a_oku en "F"))))
  (if (= tile_name "R_key") (progn (att_yaz en "R" bag_text ) (VL-CmdF "_.UpdateField" en "") (setq BB_R (a_oku en "R"))))
 )
)
(princ)
)
;-------------------------------------------------------------------------------
(defun a_bag_key_act (/)
(set_tile "tik_key" "1")
(butun_degerleri_hafizaya_al)
(setq tile_name "A_key")
(done_dialog 9)
)
(defun b_bag_key_act (/)
(set_tile "tik_key" "1")
(butun_degerleri_hafizaya_al)
(setq tile_name "B_key")
(done_dialog 9)
)
(defun c_bag_key_act (/)
(set_tile "tik_key" "1")
(butun_degerleri_hafizaya_al)
(setq tile_name "C_key")
(done_dialog 9)
)
(defun d_bag_key_act (/)
(set_tile "tik_key" "1")
(butun_degerleri_hafizaya_al)
(setq tile_name "D_key")
(done_dialog 9)
)
(defun e_bag_key_act (/)
(set_tile "tik_key" "1")
(butun_degerleri_hafizaya_al)
(setq tile_name "E_key")
(done_dialog 9)
)
(defun f_bag_key_act (/)
(set_tile "tik_key" "1")
(butun_degerleri_hafizaya_al)
(setq tile_name "F_key")
(done_dialog 9)
)
(defun r_bag_key_act (/)
(set_tile "tik_key" "1")
(butun_degerleri_hafizaya_al)
(setq tile_name "R_key")
(done_dialog 9)
)
;-------------------------------------------------------------------------------
;-------------------------------------------------------------------------------
;-------------------------------------------------------------------------------
;poz_image_key
(defun poz_image_key_act ( sldname / )
(setq sldname (strcat source_path "Standard/PZ_" sldname ".sld"))
(if (not (findfile sldname)) (setq sldname (strcat source_path "Standard/PZ_99.sld")))
(setq width (dimx_tile "poz_image_key")   height (dimy_tile "poz_image_key") )
(start_image "poz_image_key")
(fill_image   0  0  width height  300      )
(slide_image  0  0  width height  sldname  )
(end_image)
)
;-------------------------------------------------------------------------------
(defun adet_bag_key_act (/)
(butun_degerleri_hafizaya_al)
(done_dialog 10)
)
;-------------------------------------------------------------------------------
(defun adet_bag_key_action  (/)
(SetVar "CmdEcho" 0)
(setq yaz_olc (GETVAR "DIMLFAC" ))
(setq adet_bag_text nil)
(if (= (getvar "FIELDDISPLAY") 0) (setvar "FIELDDISPLAY" 1)) ;1 arka tarafi beyaz gosterir
(setq aralik_h (ATOF (a_oku en "ARALIK")))
(if (<= aralik_h 0 )
 (alert "\n Adet hesaplanamaz donati araliği uygun degil...!!! ")
 (progn
  (setq Poz_Obj_Aralik_id (itoa (att_prop_oku en "ARALIK" "ObjectId")))
  (setq line_en (car (entsel "\n Adet hesaplanacak tarama alani...   ")))
  (if (/= line_en nil)
   (progn
    (setq Bag_Obj_vba_id (itoa (vlax-get-property (vlax-ename->vla-object line_en) 'ObjectId)))
    (IF (or
        (= "LINE"       (CDR (ASSOC 0 (entget line_en))))
        (= "LWPOLYLINE" (CDR (ASSOC 0 (entget line_en))))
                                                        )
                                                         (setq adet_bag_text (strcat "%<\\AcExpr ((%<\\AcObjProp Object(%<\\_ObjId " Bag_Obj_vba_id ">%).Length      >%/%<\\AcObjProp Object(%<\\_ObjId " Poz_Obj_Aralik_id ">%).TextString>% )+1) \\f ""%lu2%pr0"">%")))
    (IF (= "DIMENSION" (CDR (ASSOC 0 (entget line_en)))) (setq adet_bag_text (strcat "%<\\AcExpr ((%<\\AcObjProp Object(%<\\_ObjId " Bag_Obj_vba_id ">%).Measurement >%/%<\\AcObjProp Object(%<\\_ObjId " Poz_Obj_Aralik_id ">%).TextString>% )+1) \\f ""%lu2%pr0"">%")))
   )
  )
  (if (= adet_bag_text nil)
    (alert "\n Adet hesaplanamaz, secilen obje uygun degil...!!! ")
      (progn
        (att_field_sil en "TB" )
        (if (> (strlen adet_carp) 0) (setq adet_carp_ (strcat adet_carp "x")) (setq adet_carp_ "" ))
        (if (> (strlen aralik)    0) (setq aralik_    (strcat "/" aralik   )) (setq aralik_    "" ))
        (setq tb (strcat adet_carp_ adet_bag_text fi cap aralik_))
        (att_yaz en "TB" tb   )
        (VL-CmdF "_.UpdateField" en ""  )
        (setq tb   (a_oku en "TB"      ))
        (setq adet (poz_edit_adet tb   ))
      )
  )
 )
)
(princ)
)
;-------------------------------------------------------------------------------
(defun adet_icin_boy_oku (en2 / )
(setq adet_al_boy 0)
  (if (= (CDR (ASSOC 0 (entget en2))) "TEXT"       )  (setq adet_al_boy (ATOF (cdr (assoc 1 (entget en2))))))
  (if (= (CDR (ASSOC 0 (entget en2))) "LINE"       )  (setq adet_al_boy (* yaz_olc (distance (cdr (assoc 10 (entget en2))) (cdr (assoc 11 (entget en2)))))))
  (if (= (CDR (ASSOC 0 (entget en2))) "LWPOLYLINE" )  (setq adet_al_boy (* yaz_olc (vlax-curve-getDistatParam en2 (vlax-curve-getEndParam en2)))))
  (if (= (CDR (ASSOC 0 (entget en2))) "ARC"        )  (setq adet_al_boy (* yaz_olc (vlax-curve-getDistatParam en2 (vlax-curve-getEndParam en2)))))
  (if
    (or
      (= (CDR (ASSOC 0 (entget en2))) "DIMENSION"             )
      (= (CDR (ASSOC 0 (entget en2))) "ARC_DIMENSION"         )
      (= (CDR (ASSOC 0 (entget en2))) "LARGE_RADIAL_DIMENSION")
    )
      (setq adet_al_boy (cdr (assoc 42 (entget en2))))
  )
adet_al_boy
)
;-------------------------------------------------------------------------------
(defun adet_al_key_act (/)
(butun_degerleri_hafizaya_al)
(done_dialog 6)
)
;-------------------------------------------------------------------------------
(defun adet_al_key_action  (/)
(setq aralik_h    0)
(setq adet_al_boy 0)
(setq adet_eski adet)
(princ "\n Adet hesaplanacak tarama alani cizgisi... ")
(setq eset_en2 (ssget))
(if (/= eset_en2 nil)
 (progn
  (setq eset_adet (sslength eset_en2))
  (setq aralik_h (atof (boy_a_oku_isle aralik)))
  (SETQ yaz_olc (GETVAR "DIMLFAC" ))
;
   (setq i 0)
   (setq adet_al_boy_t 0)
   (while (< i (sslength eset_en2))
    (setq en2 (ssname eset_en2 i))
    (setq adet_al_boy (adet_icin_boy_oku en2))
    (setq adet_al_boy_t (+ adet_al_boy_t adet_al_boy))
    (setq i (1+ i))
   )
   (setq adet_al_boy adet_al_boy_t)
;
   (if (or (= aralik_h 0) (= adet_al_boy 0))
   (alert "\n Adet hesaplanamadi. Aralik bilgisini guncelleyin....")
   (progn
   (setq adet (rtos (+ (fix (+ (/ adet_al_boy aralik_h) 0.75 )) eset_adet) 2 0))
   (princ "\n Adet basariyla guncellendi \n")
   (if (= adet adet_eski) (princ " Ama adet oncekiyle ayni cikti... \n"))
   )
  )
 )
 (progn
 (setq aralik_h (atof (boy_a_oku_isle aralik)))
 (SETQ yaz_olc (GETVAR "DIMLFAC" ))
 (setq adet_al_boy (getdist "\n Mesafe isaretleyin..."))
   (if (or (= aralik_h 0) (= adet_al_boy 0))
    (alert "\n Adet hesaplanamadi....")
    (progn
    (setq adet (rtos (+ (fix (+ (/ adet_al_boy aralik_h) 0.75 )) eset_adet) 2 0))
    (princ "\n Adet basariyla guncellendi \n")
    (if (= adet adet_eski) (princ " Ama adet oncekiyle aynı cikti... \n"))
    )
   )
  )
)
(princ)
)
;-------------------------------------------------------------------------------
; Unicode karakter okumada sorun cikiyor.
(defun not_key_act (/)
;(setq aciklama (get_tile "not_key"))
(princ)
)
;-------------------------------------------------------------------------------
(defun not_liste_key_act (/)
(set_tile "not_key" (nth (atoi (get_tile "not_liste_key")) not_liste))
(setq aciklama (nth (atoi (get_tile "not_liste_key")) not_liste))
(att_yaz en "NOT"  aciklama )
(princ)
)
;-------------------------------------------------------------------------------
(defun not_liste_coz (/)
(setq not_liste nil)
(setq dosya_adi (strcat source_path "Standard/PZ_not.txt" ))
(setq dosya (open dosya_adi "r"))
(setq okunan_yazi (read-line dosya))
 (while (/= okunan_yazi nil)
     (setq not_liste (cons okunan_yazi not_liste))
     (setq okunan_yazi (read-line dosya))
 )
(close dosya)
(setq not_liste (reverse not_liste))
(princ)
)
;-------------------------------------------------------------------------------
(defun poz_edit_pozu_duzelt ( / INS_POINT_TB INS_POINT_BOY INS_POINT_NOT)
(if (> (strlen adet_carp) 0) (setq adet_carp_ (strcat adet_carp "x")) (setq adet_carp_ ""))
(if (> (strlen aralik)    0) (setq aralik_    (strcat "/" aralik ))   (setq aralik_ ""   ))
(setq tb (strcat adet_carp_ adet fi cap aralik_))
(att_yaz en "POZ"     poz          )
(att_yaz en "TB"      tb           )
(att_yaz en "BOY"     boy          )
(att_yaz en "TIP"     tip          )
(att_yaz en "A"       BB_A         )
(att_yaz en "B"       BB_B         )
(att_yaz en "C"       BB_C         )
(att_yaz en "D"       BB_D         )
(att_yaz en "E"       BB_E         )
(att_yaz en "F"       BB_F         )
(att_yaz en "R"       BB_R         )
(att_yaz en "NOT"     aciklama     )
(att_yaz en "GC"      grup_carpani )
(att_yaz en "MALZEME" malzeme_turu )
(att_yaz en "TIK"     tik_bilgi    )
(att_yaz en "ARALIK"  aralik       )
(poz_sekil_topla en)
(VL-CmdF "_.UpdateField" en "")
(princ)
)
;-------------------------------------------------------------------------------
(defun tum_poz_gucelle_action  ( / )
(setq i 0)
(command "_.Undo" "_BE")
(princ "\n Bu poza benzetilecek...diger pozlari sec...")
(setq eset (ssget (list (cons 0 "INSERT") (cons 2 "RL-POS"))))
(princ  (sslength eset))
(while(< i (sslength eset))
(setq en2 (ssname eset i))
(if (= poz (a_oku en2 "POZ"   ))
(progn
(if (> (strlen (aralik_oku_isle (a_oku en2 "TB"  ))) 0) (setq bolu_isareti "/") (setq bolu_isareti ""))
(setq tb (strcat (substr (a_oku en2 "TB") 1 (vl-string-search fi (a_oku en2 "TB"))) fi cap bolu_isareti (aralik_oku_isle (a_oku en2 "TB"  ))))
(att_yaz en2 "TB"      tb        )
(att_yaz en2 "BOY"     boy       )
(att_yaz en2 "TIP"     TIP       )
(att_yaz en2 "A"       BB_A      )
(att_yaz en2 "B"       BB_B      )
(att_yaz en2 "C"       BB_C      )
(att_yaz en2 "D"       BB_D      )
(att_yaz en2 "E"       BB_E      )
(att_yaz en2 "F"       BB_F      )
(att_yaz en2 "R"       BB_R      )
(att_yaz en2 "TIK"  "1"  )
(att_yaz en2 "MALZEME" malzeme_turu  )
(att_yaz en2 "TIK"     "1" )
(att_yaz en2 "ARALIK"  (aralik_oku_isle (a_oku en2 "TB"  )))
(VL-CmdF "_.UpdateField" en2 "")
))
(setq i (1+ i)))
(command "_.Undo" "_E")
(gc)
(princ)
)
;-------------------------------------------------------------------------------
(defun tddk_al_key_action (/)
(fi_)
(setq en1 (car (entsel "\n Okunacak Poz' u sec..."           )))
(setq poz      (a_oku en1 "POZ"          ))
(setq cap      (cap_oku_isle    (a_oku en1 "TB")))
(setq aralik   (aralik_oku_isle (a_oku en1 "TB")))
(setq boy      (a_oku en1 "BOY"          ))
(setq tip      (a_oku en1 "TIP"          ))
(setq bb_a     (a_oku en1 "A"            ))
(setq bb_b     (a_oku en1 "B"            ))
(setq bb_c     (a_oku en1 "C"            ))
(setq bb_d     (a_oku en1 "D"            ))
(setq bb_e     (a_oku en1 "E"            ))
(setq bb_f     (a_oku en1 "F"            ))
(setq bb_r     (a_oku en1 "R"            ))
(setq aciklama (a_oku en1 "NOT"          ))
(setq malzeme_turu (a_oku en1 "MALZEME"  ))
)
;-------------------------------------------------------------------------------
(defun poz_edit_dialog_yukle (/)
(PZ_TUM_coz)
(not_liste_coz)
(setq i 0)
(while (and (/= tip (nth i tip_liste)) (/= (nth i tip_liste) nil))(setq i (1+ i)))
(if (> i (length tip_liste)) (setq i 0))
(setq tip_sira (itoa i))
   (setq Dialog_id (load_dialog (strcat source_path "Command/POSEDIT.DCL")))
   (if (not (new_dialog "poz_edit" Dialog_id)) (exit))
   (action_tile "poz_edit_cik"        "(done_dialog) (exit)"    )
   (action_tile "poz_edit_ciz"        "(progn (butun_degerleri_hafizaya_al) (done_dialog 4))"         )
   (action_tile "tum_poz_gucelle"     "(tum_poz_gucelle_act)"   )
   (action_tile "poz_key"             "(poz_key_act)"           )
   (action_tile "p_arttir_key"        "(p_arttir_key_act)"      )
   (action_tile "p_azalt_key"         "(p_azalt_key_act)"       )
   (action_tile "adet_carp_key"       "(adet_carp_key_act)"     )
   (action_tile "gc_key"              "(gc_key_act)"            )
   (action_tile "grup_c_arttir_key"   "(grup_c_arttir_key_act)" )
   (action_tile "grup_c_azalt_key"    "(grup_c_azalt_key_act)"  )
   (action_tile "adet_c_arttir_key"   "(adet_c_arttir_key_act)" )
   (action_tile "adet_c_azalt_key"    "(adet_c_azalt_key_act)"  )
   (action_tile "adet_key"            "(adet_key_act)"          )
   (action_tile "adet_al_key"         "(adet_al_key_act)"       )
   (action_tile "adet_bag_key"        "(adet_bag_key_act)"      )
   (action_tile "adet_arttir_key"     "(adet_arttir_key_act)"   )
   (action_tile "adet_azalt_key"      "(adet_azalt_key_act)"    )
   (action_tile "cap_key"             "(cap_key_act)"           )
   (action_tile "cap_arttir_key"      "(cap_arttir_key_act)"    )
   (action_tile "cap_azalt_key"       "(cap_azalt_key_act)"     )

   (action_tile "aralik_key"          "(aralik_key_act)"        )
   (action_tile "aralik_arttir_key"   "(aralik_arttir_key_act)" )
   (action_tile "aralik_azalt_key"    "(aralik_azalt_key_act)"  )

   (action_tile "boy_key"             "(boy_key_act)"           )
   (action_tile "boy_hesapla_key"     "(boy_hesapla_key_act)"   )
   (action_tile "tip_key"             "(tip_key_act)"           )
   (action_tile "tip_liste_key"       "(tip_liste_key_act)"     )
   (action_tile "A_key"               "(A_key_act)"             )
   (action_tile "B_key"               "(B_key_act)"             )
   (action_tile "C_key"               "(C_key_act)"             )
   (action_tile "D_key"               "(D_key_act)"             )
   (action_tile "E_key"               "(E_key_act)"             )
   (action_tile "F_key"               "(F_key_act)"             )
   (action_tile "R_key"               "(R_key_act)"             )
   (action_tile "a_al_key"            "(a_al_key_act)"          )
   (action_tile "b_al_key"            "(b_al_key_act)"          )
   (action_tile "c_al_key"            "(c_al_key_act)"          )
   (action_tile "d_al_key"            "(d_al_key_act)"          )
   (action_tile "e_al_key"            "(e_al_key_act)"          )
   (action_tile "f_al_key"            "(f_al_key_act)"          )
   (action_tile "r_al_key"            "(r_al_key_act)"          )
   (action_tile "a_bag_key"           "(a_bag_key_act)"         )
   (action_tile "b_bag_key"           "(b_bag_key_act)"         )
   (action_tile "c_bag_key"           "(c_bag_key_act)"         )
   (action_tile "d_bag_key"           "(d_bag_key_act)"         )
   (action_tile "e_bag_key"           "(e_bag_key_act)"         )
   (action_tile "f_bag_key"           "(f_bag_key_act)"         )
   (action_tile "r_bag_key"           "(r_bag_key_act)"         )
   (action_tile "tddk_al_key"         "(tddk_al_key_act)"       )
   (action_tile "donati_tani_key"     "(donati_tani_key_act)"   )
   (action_tile "not_key"             "(not_key_act)"           )
   (action_tile "not_liste_key"       "(not_liste_key_act)"     )
   (action_tile "malzeme_liste_key"   "(malzeme_liste_key_act)" )
   (action_tile "tik_0_key" "(set_tile \"tik_key\" \"0\")"      )
   (action_tile "tik_1_key" "(set_tile \"tik_key\" \"1\")"      )
   (set_tile "poz_key"       poz)
   (set_tile "cap_key"       cap)
   (set_tile "aralik_key"    aralik)
   (set_tile "adet_key"      adet)
   (set_tile "adet_carp_key" adet_carp)
   (set_tile "gc_key"        grup_carpani)
   (set_tile "boy_key"       boy)
   (set_tile "tip_key"       tip)
   (set_tile "A_key"         bb_a)
   (set_tile "B_key"         bb_b)
   (set_tile "C_key"         bb_c)
   (set_tile "D_key"         bb_d)
   (set_tile "E_key"         bb_e)
   (set_tile "F_key"         bb_f)
   (set_tile "R_key"         bb_r)
   (set_tile "not_key"       aciklama)
   (set_tile "malzeme_key"   malzeme_turu)
   (set_tile "tik_key"       tik_bilgi)
;
   (if (> (strlen adet_carp) 0) (setq adet_carp_ (strcat adet_carp "x")) (setq adet_carp_ ""))
   (if (> (strlen aralik)    0) (setq aralik_    (strcat "/" aralik ))   (setq aralik_ ""   ))
   (setq poz_toplam_goruntu (strcat "( " poz " )   " adet_carp_ adet " \\U+00D8 " cap aralik_ "   " boy))
;
   (start_list  "malzeme_liste_key" )
   (mapcar 'add_list  malzeme_tur_listesi )
   (end_list)
   (set_tile "malzeme_liste_key" "0")
   (set_tile "poz_toplam_goruntu" poz_toplam_goruntu)
   (start_list  "tip_liste_key" )
   (mapcar 'add_list  tip_liste )
   (end_list)
   (set_tile "tip_liste_key" tip_sira)
   (start_list  "not_liste_key" )
   (mapcar 'add_list  not_liste )
   (end_list)
   (set_tile "not_liste_key" "0")
   (poz_image_key_act tip)
   (setq dialog-state (start_dialog))
   (if (= dialog-state  4) (poz_edit_pozu_duzelt))
   (if (= dialog-state  5) (progn (bukum_boyu_al) (boy_hesapla_key_act)  (poz_edit_dialog_yukle)))
   (if (= dialog-state  6) (progn (adet_al_key_action)                   (poz_edit_dialog_yukle)))
   (if (= dialog-state  7) (progn (tum_poz_gucelle_action)               (poz_edit_dialog_yukle)))
   (if (= dialog-state  8) (progn (tddk_al_key_action)                   (poz_edit_dialog_yukle)))
   (if (= dialog-state  9) (progn (bukum_boyu_bagla)(boy_hesapla_key_act)(poz_edit_dialog_yukle)))
   (if (= dialog-state 10) (progn (adet_bag_key_action)                  (poz_edit_dialog_yukle)))
   (if (= dialog-state 11) (progn (donati_tani_key_action)               (poz_edit_dialog_yukle)))

(unload_dialog Dialog_id)
)
;-------------------------------------------------------------------------------
(defun visibility_RL-POS2 ( en / )
   (setvar "cmdecho" 0 )
   (setvar "dimzin"  1 )
    (setq tb_visibility  (att_prop_oku en "TB"  "Invisible"))
    (setq not_visibility (att_prop_oku en "NOT" "Invisible"))
       (if (and (= tb_visibility :vlax-true ) (= not_visibility :vlax-true )) (att_prop_yaz en "TB"  "Invisible" "false" ) )
       (if (and (= tb_visibility :vlax-false) (= not_visibility :vlax-true )) (att_prop_yaz en "NOT" "Invisible" "false" ) )
       (if (and (= tb_visibility :vlax-false) (= not_visibility :vlax-false)) (att_prop_yaz en "TB"  "Invisible" "true"  ) )
       (if (and (= tb_visibility :vlax-true ) (= not_visibility :vlax-false)) (att_prop_yaz en "NOT" "Invisible" "true"  ) )
       (pozbilgi_sekil_topla en)
   (VL-CmdF "_.UpdateField" en "")
   (setvar "clayer" clayer_old)
   (setvar "dimzin" dimzin_old)
   (setvar "cmdecho" 1)
   (gc)
   (gc)
   (gc)
   (princ)
   (exit)
)
;-------------------------------------------------------------------------------
(defun c:ee ( / )
(vl-load-com)
(setq malzeme_tur_listesi '( "A500C" "A-I" "A-II" "A-III" "A-IIIc" ))
(RENAISSANCE_metraj_layer_olustur)
(setq dimzin_old (getvar "dimzin"))
(setq clayer_old (getvar "clayer"))
(setq yeni_poz 0)
(princ "Poz seciniz.....")
(setq ent (ssget ":S" (list (cons 0 "INSERT") (cons -4  "<OR") (cons 2 "RL-POS") (cons 2 "RL-POS2") (cons -4  "OR>") )))
(setvar "cmdecho" 0 )
(setvar "dimzin"  1 )
(setvar "attreq"  0 )
(if (= ent nil)
(progn
(setq yeni_poz 1)
(setq poz_insert (getpoint "\n Yeni poz insert noktasi... "))
(setq ins_scale (* (/ (OLCEK_OKU) (BIRIM_OKU)) 100))
      (setvar "clayer" "ren.mtr.tb" )
(command "-insert" (strcat source_path "Standard/RL-POS.dwg") poz_insert ins_scale ins_scale 0 )
(setq en (entlast))
)
(setq en (ssname ent 0 ))
)
(if (= (cdr (assoc 2 (entget en))) "RL-POS2")
  (visibility_RL-POS2 en)
)
(fi_)
(setq poz          (a_oku en "POZ" ))
(setq tb           (a_oku en "TB"  ))
(setq adet_carp    (poz_edit_adet_carpi tb))
(setq adet         (poz_edit_adet       tb))
(setq cap          (poz_edit_cap        tb))
(setq aralik       (poz_edit_aralik     tb))
(setq boy          (a_oku en "BOY" ))
(setq tip          (a_oku en "TIP" ))
(setq BB_A         (a_oku en "A"   ))
(setq BB_B         (a_oku en "B"   ))
(setq BB_C         (a_oku en "C"   ))
(setq BB_D         (a_oku en "D"   ))
(setq BB_E         (a_oku en "E"   ))
(setq BB_F         (a_oku en "F"   ))
(setq BB_R         (a_oku en "R"   ))
(setq aciklama     (a_oku en "NOT" ))
; vl-string->list "blabla"
; vl-list->string "ascii kod"
(setq grup_carpani (a_oku en "GC"  ))
(setq malzeme_turu (a_oku en "MALZEME"))
(setq tik_bilgi    (a_oku en "TIK" ))
(poz_edit_dialog_yukle)
(if (= yeni_poz 1)(command "rotate" (entlast) "" (cdr (assoc 10 (entget (entlast))))))
(setvar "clayer" clayer_old)
(setvar "dimzin" dimzin_old)
(setvar "cmdecho" 1)
(gc)
(gc)
(gc)
(princ)
)
;--------------------------------------------------------------------------------------------------------------------------------------------------------
