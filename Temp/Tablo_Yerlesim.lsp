;------------------------------------------------------------------------------;
(defun ayarlari_ekrandan_oku_Tablo (/)
 (setq Yerlesim_1   (get_tile "Yerlesim_1"  ))
 (setq Yerlesim_2   (get_tile "Yerlesim_2"  ))
 (setq Yerlesim_3   (get_tile "Yerlesim_3"  ))
)
;-------------------------------------------------------------------------------
(defun ayarlari_ekrana_yaz_Tablo (/)
 (set_tile "Yerlesim_1" Yerlesim_1 )
 (set_tile "Yerlesim_2" Yerlesim_2 )
 (set_tile "Yerlesim_3" Yerlesim_3 )

(yerlesim_image_1_act)
(yerlesim_image_2_act)
(yerlesim_image_3_act)
)
;-------------------------------------------------------------------------------
(defun ayarlari_dosyaya_yaz2_Tablo (/)
 (setq dosya (open (strcat client_path "Standard/Tablo_Tipi.TXT" ) "w"))
 (princ Yerlesim_12 dosya )(princ "\n" dosya)
 (princ Yerlesim_22 dosya )(princ "\n" dosya)
 (princ Yerlesim_32 dosya )(princ "\n" dosya)
 (close dosya)
)
;-------------------------------------------------------------------------------
(defun ayarlari_dosyaya_yaz_Tablo (/)
 (setq dosya (open (strcat client_path "Standard/Tablo_Tipi.TXT" ) "w"))
 (princ Yerlesim_1 dosya )(princ "\n" dosya)
 (princ Yerlesim_2 dosya )(princ "\n" dosya)
 (princ Yerlesim_3 dosya )(princ "\n" dosya)
 (close dosya)
)
;-------------------------------------------------------------------------------
(defun ayarlari_dosyadan_oku_Tablo (/)
 (if (= (not (open (strcat client_path "Standard/Tablo_Tipi.TXT") "r")) t )
 (progn (setq dosya (open (strcat client_path "Standard/Tablo_Tipi.TXT") "w"))
 (princ "1" dosya )(princ "\n" dosya)
 (princ "0" dosya )(princ "\n" dosya)
 (princ "0" dosya )(princ "\n" dosya)
 (close dosya)))
 (setq dosya (open (strcat client_path "Standard/Tablo_Tipi.TXT") "r"))
 (setq Yerlesim_1 (read-line dosya) )
 (setq Yerlesim_2 (read-line dosya) )
 (setq Yerlesim_3 (read-line dosya) )
 (close dosya)
)
;-------------------------------------------------------------------------------
(defun ayarlari_dosyadan_oku2_Tablo (/)
 (setq dosya (open (strcat client_path "Standard/Tablo_Tipi.TXT") "r"))
  (setq Yerlesim_12 (read-line dosya) )
  (setq Yerlesim_22 (read-line dosya) )
  (setq Yerlesim_32  (read-line dosya) )
 (close dosya)
)
;-------------------------------------------------------------------------------
(defun yerlesim_image_1_act ( /)
(setq sldname (strcat source_pathlisp "Ayar/Yerlesim_1.sld"))
(setq width (dimx_tile "yerlesim_image")   height (dimy_tile "yerlesim_image") )
(start_image "yerlesim_image")
(fill_image   0  0  700 height  300      )
(slide_image  0  0  700 height  sldname  )
(end_image)
)
;-------------------------------------------------------------------------------
(defun yerlesim_image_2_act ( /)
(setq sldname (strcat source_pathlisp "Ayar/Yerlesim_2.sld"))
(setq width (dimx_tile "yerlesim_image_2")   height (dimy_tile "yerlesim_image_2") )
(start_image "yerlesim_image_2")
(fill_image   0  0  700 height  300      )
(slide_image  0  0  700 height  sldname  )
(end_image)
)
;-------------------------------------------------------------------------------
(defun yerlesim_image_3_act ( /)
(setq sldname (strcat source_pathlisp "Ayar/Yerlesim_3.sld"))
(setq width (dimx_tile "yerlesim_image_3")   height (dimy_tile "yerlesim_image_3") )
(start_image "yerlesim_image_3")
(fill_image   0  0  700 height  300      )
(slide_image  0  0  700 height  sldname  )
(end_image)
)
;-------------------------------------------------------------------------------
(defun Yerlesim_1_act ( / )
 (ayarlari_ekrandan_oku_Tablo)
 (ayarlari_dosyaya_yaz_Tablo)
)
;-------------------------------------------------------------------------------
(defun Yerlesim_2_act ( / )
 (ayarlari_ekrandan_oku_Tablo)
 (ayarlari_dosyaya_yaz_Tablo)
)
;-------------------------------------------------------------------------------
(defun Yerlesim_3_act ( / )
 (ayarlari_ekrandan_oku_Tablo)
 (ayarlari_dosyaya_yaz_Tablo)
)
;-------------------------------------------------------------------------------
(defun ayarlari_dosyaya_yaz2_Tablo_act  ( / )
 ;(ayarlari_dosyadan_oku2)
 (ayarlari_dosyaya_yaz2_Tablo)
 (done_dialog 5) ; Dialog state
)
;-------------------------------------------------------------------------------
(defun ayarla_Tablo_act  ( / )
 (ayarlari_ekrandan_oku_Tablo)
 (ayarlari_dosyaya_yaz_Tablo)
 (done_dialog 4) ; Dialog state
)
;-------------------------------------------------------------------------------
; If dialog state equal 4 write this place....
(defun ayarla_action_Tablo ( / )
(princ)
)
;------------------------------------------------------------------------------;
(defun M_T_Y_act ()
  (setq dcl_id1 (load_dialog (strcat source_path "Command/Unw.dcl")))
  (if (not (new_dialog "nest1" dcl_id1))(exit))
 (action_tile "Yerlesim_1"    "(Yerlesim_1_act)"   )
 (action_tile "Yerlesim_2"    "(Yerlesim_2_act)"   )
 (action_tile "Yerlesim_3"    "(Yerlesim_3_act)"     )
 (action_tile "cancel"        " (done_dialog) (ayarlari_dosyaya_yaz2_Tablo_act)")
 (action_tile "accept"        " (done_dialog)")
 (ayarlari_dosyadan_oku_Tablo)
 (ayarlari_dosyadan_oku2_Tablo)
 (ayarlari_ekrana_yaz_Tablo)
  (start_dialog)
  (unload_dialog dcl_id1)
  (princ)
)
