;--------------------------------------------------------------------------------------------------------------------------------------------------------
;--------------------------------------------------------------------------------------------------------------------------------------------------------
;--------------------------------------------------------------------------------------------------------------------------------------------------------
;--------------------------------------------------------------------------------------------------------------------------------------------------------
;--------------------------------------------------------------------------------------------------------------------------------------------------------
(defun cp_ag ( cp / cp ) (* 0.00616537558266997 (* cp cp)))
;--------------------------------------------------------------------------------------------------------------------------------------------------------
(defun r_b_h (cap) (if (> cap 20) (* cap 3.5) (* cap 2.0)))
;--------------------------------------------------------------------------------------------------------------------------------------------------------
(defun m_b_h (cap) (if (> cap 20) (* cap 7.0) (* cap 4.0)))
;--------------------------------------------------------------------------------------------------------------------------------------------------------
(defun min_boy (boy / )
(setq boy_isle_2 (vl-string-translate "-~" "  " boy))
  (if (= boy boy_isle_2)
    (setq boy boy_isle_2)
    (setq boy (rtos (eval (read (strcat "(min " boy_isle_2 ")"))) 2 0))
  )
boy
)
;--------------------------------------------------------------------------------------------------------------------------------------------------------
(defun max_boy (boy / )
(setq boy_isle_2 (vl-string-translate "-~" "  " boy))
  (if (= boy boy_isle_2)
    (setq boy boy_isle_2)
    (setq boy (rtos (eval (read (strcat "(max " boy_isle_2 ")"))) 2 0))
  )
boy
)
;--------------------------------------------------------------------------------------------------------------------------------------------------------
(defun b_h (tip A B C D E F BR cap / )
(setq a_min (ATOF (min_boy A)))
(setq a_max (ATOF (max_boy A)))
(setq b_min (ATOF (min_boy B)))
(setq b_max (ATOF (max_boy B)))
(setq c_min (ATOF (min_boy C)))
(setq c_max (ATOF (max_boy C)))
(setq d_min (ATOF (min_boy D)))
(setq d_max (ATOF (max_boy D)))
(setq e_min (ATOF (min_boy E)))
(setq e_max (ATOF (max_boy E)))
(setq f_min (ATOF (min_boy F)))
(setq f_max (ATOF (max_boy F)))
(setq r (r_b_h cap))
(if (= PZ_TUM nil) (PZ_TUM_coz))
(setq j 0)
(while (and (< j (length tip_liste))(/= tip (nth j tip_liste))) (setq j (1+ j)))
(if (= tip (nth j tip_liste))
    (progn
    (setq CARP_A   (atof (nth  2 (nth j PZ_TUM))))
    (setq CARP_B   (atof (nth  3 (nth j PZ_TUM))))
    (setq CARP_C   (atof (nth  4 (nth j PZ_TUM))))
    (setq CARP_D   (atof (nth  5 (nth j PZ_TUM))))
    (setq CARP_E   (atof (nth  6 (nth j PZ_TUM))))
    (setq CARP_F   (atof (nth  7 (nth j PZ_TUM))))
    (setq CARP_BR  (atof (nth  8 (nth j PZ_TUM))))
    (setq CARP_r   (atof (nth  9 (nth j PZ_TUM))))
    (setq CARP_cap (atof (nth 10 (nth j PZ_TUM))))
    (setq boy_hesap_min (+ (* CARP_A A_min) (* CARP_B B_min) (* CARP_C C_min) (* CARP_D D_min) (* CARP_E E_min) (* CARP_F F_min) (* CARP_BR BR)))
    (setq boy_hesap_max (+ (* CARP_A A_max) (* CARP_B B_max) (* CARP_C C_max) (* CARP_D D_max) (* CARP_E E_max) (* CARP_F F_max) (* CARP_BR BR)))
    (if (= tip "77") (progn (setq boy_hesap_min (* a_min boy_hesap_min)) (setq boy_hesap_max (* a_max boy_hesap_max))))
    (if (= boy_hesap_min boy_hesap_max)
        (setq boy_hesap (strcat "L="  (RTOS boy_hesap_min 2 0)))
        (setq boy_hesap (strcat "L="  (RTOS boy_hesap_min 2 0) "~" (RTOS boy_hesap_max 2 0)))
    )
   )
    (setq boy_hesap "L=")
  )


boy_hesap
)
;--------------------------------------------------------------------------------------------------------------------------------------------------------
(defun b_h_check (poz tip A B C D E F r1 / )
(setq a1 (ATOF (min_boy A)))
(setq b1 (ATOF (min_boy B)))
(setq c1 (ATOF (min_boy C)))
(setq d1 (ATOF (min_boy D)))
(setq e1 (ATOF (min_boy E)))
(setq f1 (ATOF (min_boy F)))
(setq j 0)
(while (and (< j (length tip_liste))(/= tip (nth j tip_liste))) (setq j (1+ j)))
                                 (if (= tip (nth j tip_liste))
                                     (progn
                                      (setq a2   (atof (nth  2 (nth j PZ_TUM))))
                                      (setq b2   (atof (nth  3 (nth j PZ_TUM))))
                                      (setq c2   (atof (nth  4 (nth j PZ_TUM))))
                                      (setq d2   (atof (nth  5 (nth j PZ_TUM))))
                                      (setq e2   (atof (nth  6 (nth j PZ_TUM))))
                                      (setq f2   (atof (nth  7 (nth j PZ_TUM))))
                                      (setq r2   (atof (nth  8 (nth j PZ_TUM))))
                                     )
                                 )
(if (and ( = a1 0) (/= a2 0)) (princ (strcat "\n No: " poz ", Tip: " tip " A bending length entered.")   ))
(if (and (/= a1 0) ( = a2 0)) (princ (strcat "\n No: " poz ", Tip: " tip " A bending length multiplier zero.")))
(if (and ( = b1 0) (/= b2 0)) (princ (strcat "\n No: " poz ", Tip: " tip " B bending length entered.")   ))
(if (and (/= b1 0) ( = b2 0)) (princ (strcat "\n No: " poz ", Tip: " tip " B bending length multiplier zero.")))
(if (and ( = c1 0) (/= c2 0)) (princ (strcat "\n No: " poz ", Tip: " tip " C bending length entered.")   ))
(if (and (/= c1 0) ( = c2 0)) (princ (strcat "\n No: " poz ", Tip: " tip " C bending length multiplier zero.")))
(if (and ( = d1 0) (/= d2 0)) (princ (strcat "\n No: " poz ", Tip: " tip " D bending length entered.")   ))
(if (and (/= d1 0) ( = d2 0)) (princ (strcat "\n No: " poz ", Tip: " tip " D bending length multiplier zero.")))
(if (and ( = e1 0) (/= e2 0)) (princ (strcat "\n No: " poz ", Tip: " tip " E bending length entered.")   ))
(if (and (/= e1 0) ( = e2 0)) (princ (strcat "\n No: " poz ", Tip: " tip " E bending length multiplier zero.")))
(if (and ( = f1 0) (/= f2 0)) (princ (strcat "\n No: " poz ", Tip: " tip " F bending length entered.")   ))
(if (and (/= f1 0) ( = f2 0)) (princ (strcat "\n No: " poz ", Tip: " tip " F bending length multiplier zero.")))
(if (and ( = r1 0) (/= r2 0)) (princ (strcat "\n No: " poz ", Tip: " tip " R bending length entered.")   ))
(if (and (/= r1 0) ( = r2 0)) (princ (strcat "\n No: " poz ", Tip: " tip " R bending length multiplier zero.")))
)
;--------------------------------------------------------------------------------------------------------------------------------------------------------
(defun PZ_TUM_coz ( / s1 s2 i n l1 l2 eleman deger boy dosya_adi)
(setq s1 ";")
(setq grup nil)
(setq grup_liste nil)
(setq PZ_TUM nil)
(setq dosya_adi (strcat (strcat source_path "Standard/PZ_TUM.txt" )))
(setq dosya (open dosya_adi "r"))
(setq s2    (read-line dosya))
 (while (/= s2 nil)
   (setq i           1  )
   (setq n           1  )
   (setq l1 (strlen s1) )
   (setq l2 (strlen s2) )
   (setq eleman    nil  )
       (while (<= i l2)
          (if (= (substr s2 i l1) s1)
             (progn
               (setq boy  (- i n 1))
               (if (< boy 0 ) (setq boy 0))
               (setq deger    (substr s2 (+ n 1) boy))
               (setq eleman   (cons deger eleman))
               (setq n  i )
             )
          )
          (setq i (+ i 1) )
       )
    (setq eleman    (reverse eleman) )
    (setq s2       (read-line dosya) )
      (if (/= eleman nil )
        (progn
        (setq grup       (cons eleman grup))
        (setq grup_liste (cons (cadr eleman) grup_liste))
        )
      )
 )
(close dosya)
(princ)
    (setq tip_liste (reverse grup_liste))
    (setq PZ_TUM    (reverse grup))
)
(defun min_boy (boy / )
(setq boy_isle_2 (vl-string-translate "-~" "  " boy))
  (if (= boy boy_isle_2)
    (setq boy boy_isle_2)
    (setq boy (rtos (eval (read (strcat "(min " boy_isle_2 ")"))) 2 0))
  )
boy
)
;--------------------------------------------------------------------------------------------------------------------------------------------------------
(defun hata_kontrol ( toplam_bilgi / )
(if (= PZ_TUM nil) (PZ_TUM_coz))
;--------------------------------------------------------------------------------------------------------------------------
(setq i 0)
(repeat  (- (length toplam_bilgi) 1)
(if          (and ( = (cdr (assoc  1 (nth i toplam_bilgi))) (cdr (assoc  1 (nth (+ i 1) toplam_bilgi))))
                  (/= (cdr (assoc  3 (nth i toplam_bilgi))) (cdr (assoc  3 (nth (+ i 1) toplam_bilgi)))))
(progn
(princ   (strcat "\n "(cdr (assoc  1 (nth i toplam_bilgi))) ".Pose Diameter failure. Re-do the correct quantity....! "))
)
)
(if          (and ( = (cdr (assoc  1 (nth i toplam_bilgi))) (cdr (assoc  1 (nth (+ i 1) toplam_bilgi))))
                  (/= (cdr (assoc  5 (nth i toplam_bilgi))) (cdr (assoc  5 (nth (+ i 1) toplam_bilgi)))))
(progn
(princ   (strcat "\n "(cdr (assoc  1 (nth i toplam_bilgi))) ".Pose Total length error has occurred. Re-do the correct quantity....! "))
)
)
(if          (and ( = (cdr (assoc  1 (nth i toplam_bilgi))) (cdr (assoc  1 (nth (+ i 1) toplam_bilgi))))
                  (/= (cdr (assoc  6 (nth i toplam_bilgi))) (cdr (assoc  6 (nth (+ i 1) toplam_bilgi)))))
(progn
(princ   (strcat "\n "(cdr (assoc  1 (nth i toplam_bilgi))) ".Pose Type error has occurred. Re-do the correct quantity....! "))
)
)
(if          (and ( = (cdr (assoc  1 (nth i toplam_bilgi))) (cdr (assoc  1 (nth (+ i 1) toplam_bilgi))))
              (or
                  (/= (cdr (assoc  7 (nth i toplam_bilgi))) (cdr (assoc  7 (nth (+ i 1) toplam_bilgi))))
                  (/= (cdr (assoc  8 (nth i toplam_bilgi))) (cdr (assoc  8 (nth (+ i 1) toplam_bilgi))))
                  (/= (cdr (assoc  9 (nth i toplam_bilgi))) (cdr (assoc  9 (nth (+ i 1) toplam_bilgi))))
                  (/= (cdr (assoc 10 (nth i toplam_bilgi))) (cdr (assoc 10 (nth (+ i 1) toplam_bilgi))))
                  (/= (cdr (assoc 11 (nth i toplam_bilgi))) (cdr (assoc 11 (nth (+ i 1) toplam_bilgi))))
                  (/= (cdr (assoc 12 (nth i toplam_bilgi))) (cdr (assoc 12 (nth (+ i 1) toplam_bilgi))))
                  (/= (cdr (assoc 13 (nth i toplam_bilgi))) (cdr (assoc 13 (nth (+ i 1) toplam_bilgi))))))
(progn
(princ   (strcat "\n "(cdr (assoc  1 (nth i toplam_bilgi))) ".Pose Bending length error. Re-do the correct quantity....! "))
)
)
(setq i (1+ i))
(princ)
)
; Bireysel kontroller.
(setq i 0)
(repeat  (length toplam_bilgi)
; Büküm boyu kontrolleri.
(b_h_check
                                   (cdr (assoc  1 (nth i toplam_bilgi)))
                                   (cdr (assoc  6 (nth i toplam_bilgi)))
                                   (cdr (assoc  7 (nth i toplam_bilgi)))
                                   (cdr (assoc  8 (nth i toplam_bilgi)))
                                   (cdr (assoc  9 (nth i toplam_bilgi)))
                                   (cdr (assoc 10 (nth i toplam_bilgi)))
                                   (cdr (assoc 11 (nth i toplam_bilgi)))
                                   (cdr (assoc 12 (nth i toplam_bilgi)))
                             (atof (cdr (assoc 13 (nth i toplam_bilgi))))
)
; Toplam boy hesabının doğruluğu kontrolü
(setq boy (atof (boy_oku_isle (b_h (cdr (assoc  6 (nth i toplam_bilgi)))
                                   (cdr (assoc  7 (nth i toplam_bilgi)))
                                   (cdr (assoc  8 (nth i toplam_bilgi)))
                                   (cdr (assoc  9 (nth i toplam_bilgi)))
                                   (cdr (assoc 10 (nth i toplam_bilgi)))
                                   (cdr (assoc 11 (nth i toplam_bilgi)))
                                   (cdr (assoc 12 (nth i toplam_bilgi)))
                             (atof (cdr (assoc 13 (nth i toplam_bilgi))))
                             (atof (cdr (assoc  3 (nth i toplam_bilgi))))))))
(if (and (/= (cdr (assoc  6 (nth i toplam_bilgi))) "99") (/= (fix boy)  (cdr (assoc 14 (nth i toplam_bilgi)))))
(progn
(princ   (strcat "\n "(cdr (assoc 1 (nth i toplam_bilgi))) ".Pose Bending length is calculated tribes <L=" (itoa (fix boy)) "> what exists <L=" (itoa (cdr (assoc 14 (nth i toplam_bilgi)))) "> different...! "))
)
)
; Toplam boyun sıfır olması kontrolü
(if (= (cdr (assoc 14 (nth i toplam_bilgi))) 0)
(progn
(princ   (strcat "\n "(cdr (assoc 1 (nth i toplam_bilgi))) ".Pose Total length L=0 ! "))
)
)
; Toplam boyun 12m yi geçmesi kontrolü
(if (> (* olcu_carp (cdr (assoc 14 (nth i toplam_bilgi)))) 12)
(progn
(princ   (strcat "\n "(cdr (assoc 1 (nth i toplam_bilgi))) ".Pose Twist tribes goes exceed the calculated length 12m ! "))
)
)
(setq i (1+ i))
)
; Hata kontrolleri sonu
;--------------------------------------------------------------------------------------------------------------------------
(princ)
)
;--------------------------------------------------------------------------------------------------------------------------------------------------------
(defun fi_ (/) (setq fi "%%C" ))
;--------------------------------------------------------------------------------------------------------------------------------------------------------
(defun boy_oku_isle (boy / )
(setq boy_isle_1 (vl-string-translate "lL=" "   " boy))
(setq boy_isle_2 (vl-string-translate "-~" "  " boy_isle_1))
  (if (= boy_isle_1 boy_isle_2)
    (setq boy boy_isle_1)
    (setq boy (rtos (eval (read (strcat "(* 0.5 (+ " boy_isle_2 "))"))) 2 2))
  )
boy
)
;--------------------------------------------------------------------------------------------------------------------------------------------------------
(defun boy_a_oku_isle (boy / )
(setq boy_isle_2 (vl-string-translate "-~" "  " boy))
  (if (= boy boy_isle_2)
    (setq boy boy_isle_2)
    (setq boy (rtos (eval (read (strcat "(* 0.5 (+ " boy_isle_2 "))"))) 2 0))
  )
boy
)
;--------------------------------------------------------------------------------------------------------------------------------------------------------
(defun adet_oku_isle (tb / )
(fi_)
(setq fi_boyu (strlen fi))
(setq fi_yeri (vl-string-search fi tb))
(setq adet_isle_1 (vl-string-translate "xX" "  " (substr tb 1 fi_yeri)))
  (if (= adet adet_isle_1)
    (setq adet adet_isle_1)
    (setq adet (rtos (eval (read (strcat "(* " adet_isle_1 ")"))) 2 0))
  )
adet
)
;--------------------------------------------------------------------------------------------------------------------------------------------------------
(defun cap_oku_isle (tb / )
(fi_)
(setq fi_boyu (strlen fi))
(setq tb_boyu (strlen tb))
(setq fi_yeri (vl-string-search fi   tb      ))
(setq b_yeri  (vl-string-search "/"  tb      ))
(if (= b_yeri nil) (setq b_yeri (+ 1 (strlen tb))))
(setq cap (substr tb (+ 1 fi_boyu fi_yeri)  (- b_yeri  fi_yeri fi_boyu)))
(setq cap (itoa (atoi cap)))
cap
)
;--------------------------------------------------------------------------------------------------------------------------------------------------------
(defun aralik_oku_isle (tb / )
(fi_)
(setq fi_boyu  (strlen fi))
(setq tb_boyu  (strlen tb))
(setq b_yeri   (vl-string-search "/"  tb      ))
(if (/= b_yeri nil)
        (setq aralik_b   (substr tb (+ 2 b_yeri )  (- tb_boyu b_yeri)))
        (setq aralik_b ""))
aralik_b
)
;--------------------------------------------------------------------------------------------------------------------------------------------------------
(defun a_oku (en tag /)
(vl-load-com)
(setq tag (strcase tag))
(setq deger "")
(setq blk  (vlax-ename->vla-object en))
(setq atts (vlax-invoke blk 'getattributes))
(foreach att atts
    (if (= tag (vla-get-tagstring att)) (setq deger (vla-get-textstring att)))
)
 deger
)
;--------------------------------------------------------------------------------------------------------------------------------------------------------
(defun cap_bilgi_olustur ( toplam_bilgi / )
(setq i 0)
(setq cap_liste (list))
(while(< i (length toplam_bilgi))
(setq cap  (cdr (nth  3 (nth i toplam_bilgi))))
(setq adet (cdr (nth  2 (nth i toplam_bilgi))))
(setq boy  (cdr (nth 14 (nth i toplam_bilgi))))
(setq toplam_boy (rtos (* (atof adet) boy ) 2 8))
(setq cap_ekle (list (cons 0 i ) (cons 1 cap) (cons 2 toplam_boy)))
(setq cap_liste (cons cap_ekle cap_liste))
(setq i (+ i 1))
)
(setq cap_liste (vl-sort cap_liste (function (lambda (e1 e2) (< (atoi (cdr (assoc 1 e1))) (atoi (cdr (assoc 1 e2))))))))
(setq i 0)
(setq bilgi_adet (length cap_liste))
(while(< i bilgi_adet)
(if (= (cdr (assoc 1 (nth i cap_liste))) (cdr (assoc 1 (nth (+ i 1) cap_liste))))
(progn
(setq adet_topla (rtos (+ (atof (cdr (assoc 2 (nth i cap_liste)))) (atof (cdr (assoc 2 (nth (+ i 1) cap_liste))))) 2 8))
(setq cap_liste  (subst (subst (cons 2 adet_topla) (assoc 2 (nth i cap_liste)) (nth i cap_liste)) (nth i cap_liste) cap_liste))
(setq cap_liste  (vl-remove (nth (+ i 1) cap_liste) cap_liste))
(setq bilgi_adet (- bilgi_adet 1))
(setq i (- i 1))
)
)
(setq i (+ i 1))
)
cap_liste
)
;--------------------------------------------------------------------------------------------------------------------------------------------------------
(defun RENAISSANCE_toplam_bilgi_olustur ( eset / )
(setq toplam_bilgi (list))
(setq cntr 0)
(while(< cntr (sslength eset))
(setq en (ssname eset cntr))
(setq grup_carpani (a_oku en "GC" ))
(if (= grup_carpani "") (setq grup_carpani "1"))
(setq gc_deger (atoi grup_carpani))
(setq ok_bilgi (list (cons  0  cntr  )
                     (cons  1 (a_oku en "POZ"))
                     (cons  2 (rtos (* gc_deger (atof (adet_oku_isle (a_oku en "TB" )))) 2 0 ))
                     (cons  3 (cap_oku_isle    (a_oku en "TB" )))
                     (cons  4 (aralik_oku_isle (a_oku en "TB" )))
                     (cons  5 (a_oku en "BOY" ))
                     (cons  6 (a_oku en "TIP" ))
                     (cons  7 (a_oku en "A"   ))
                     (cons  8 (a_oku en "B"   ))
                     (cons  9 (a_oku en "C"   ))
                     (cons 10 (a_oku en "D"   ))
                     (cons 11 (a_oku en "E"   ))
                     (cons 12 (a_oku en "F"   ))
                     (cons 13 (a_oku en "R"   ))
                     (cons 14 (atoi (boy_oku_isle (a_oku en "BOY" ))))
                     (cons 15 (a_oku en "MALZEME" ))

                                                                       ))

(setq toplam_bilgi (cons ok_bilgi toplam_bilgi))
(setq cntr(+ cntr 1))
)
(setq toplam_bilgi (vl-sort toplam_bilgi (function (lambda (e1 e2)      (< (atoi (cdr (assoc  1 e1))) (atoi (cdr (assoc  1 e2))))))))
(setq toplam_bilgi (vl-sort toplam_bilgi (function (lambda (e1 e2) (and (= (atoi (cdr (assoc  1 e1))) (atoi (cdr (assoc  1 e2))))
                                                                        (< (atoi (cdr (assoc  3 e1))) (atoi (cdr (assoc  3 e2)))))))))
(setq toplam_bilgi (vl-sort toplam_bilgi (function (lambda (e1 e2) (and (= (atoi (cdr (assoc  1 e1))) (atoi (cdr (assoc  1 e2))))
                                                                        (= (atoi (cdr (assoc  3 e1))) (atoi (cdr (assoc  3 e2))))
                                                                        (<       (cdr (assoc 14 e1))        (cdr (assoc 14 e2))))))))
toplam_bilgi
)
;--------------------------------------------------------------------------------------------------------------------------------------------------------
(defun RENAISSANCE_toplam_bilgi_derle ( toplam_bilgi / )
(setq i 0)
(setq bilgi_adet (length toplam_bilgi))
(while(< i bilgi_adet)
(if (and (= (cdr (assoc 1 (nth i toplam_bilgi))) (cdr (assoc 1 (nth (+ i 1) toplam_bilgi))))
         (= (cdr (assoc 3 (nth i toplam_bilgi))) (cdr (assoc 3 (nth (+ i 1) toplam_bilgi))))
         (= (cdr (assoc 5 (nth i toplam_bilgi))) (cdr (assoc 5 (nth (+ i 1) toplam_bilgi)))))
(progn
(setq adet_topla (itoa (+ (atoi (cdr (assoc 2 (nth i toplam_bilgi)))) (atoi (cdr (assoc 2 (nth (+ i 1) toplam_bilgi)))))))
(setq toplam_bilgi (subst (subst (cons 2 adet_topla) (assoc 2 (nth i toplam_bilgi)) (nth i toplam_bilgi)) (nth i toplam_bilgi) toplam_bilgi))
(setq toplam_bilgi (vl-remove (nth (+ i 1) toplam_bilgi) toplam_bilgi))
(setq bilgi_adet (- bilgi_adet 1))
(setq i (- i 1))
)
)
(setq i (+ i 1))
)
toplam_bilgi
)
;--------------------------------------------------------------------------------------------------------------------------------------------------------
(defun ren_metraj_tablo_dosya_yaz (cap_liste toplam_bilgi / en_son_toplam_agirlik anlik_tarih fname template_file cll csht rang sht nwb awb aexc)
(setq anlik_tarih (RTOS (GETVAR "CDATE") 2 6))
(setq fname (strcat (getvar "dwgprefix") (substr (getvar "dwgname") 1 (- (strlen (getvar "dwgname")) 4 )) "-" anlik_tarih ".xls"))
(setq aexc  (vlax-get-or-create-object "Excel.Application"))
(if (null aexc) (progn (alert "Excel baslatilamadi.") (exit)))
(setq  awb  (vlax-get-property  aexc "Workbooks" ))
(setq  nwb  (vlax-invoke-method awb  "Add"       ))
(setq  sht  (vlax-get-property  nwb  "Sheets"    ))
(setq  csht (vlax-get-property  sht  "Item" 1    ))
(setq  cll  (vlax-get-property  csht "Cells"     ))
(vla-put-visible aexc :vlax-false)
    (setq  row  9 ) ; Metrajın eklenmeye başlayacağı satır.
    (setq  row_num (length toplam_bilgi))
    (setq  i    0 )
      (vlax-put-property  cll "Item"   8  1 (vl-princ-to-string "Pos"   ))
      (vlax-put-property  cll "Item"   8  2 (vl-princ-to-string "Ø"     ))
      (vlax-put-property  cll "Item"   8  3 (vl-princ-to-string "Item"  ))
      (vlax-put-property  cll "Item"   8  4 (vl-princ-to-string "Length"))
    (repeat row_num
      (vlax-put-property  cll "Item" row  1 (vl-princ-to-string (cdr (assoc  1 (nth i toplam_bilgi)))))
      (vlax-put-property  cll "Item" row  2 (vl-princ-to-string (cdr (assoc  3 (nth i toplam_bilgi)))))
      (vlax-put-property  cll "Item" row  3 (vl-princ-to-string (cdr (assoc  2 (nth i toplam_bilgi)))))
      (vlax-put-property  cll "Item" row  4 (vl-princ-to-string (rtos (* olcu_carp (cdr (assoc 14 (nth i toplam_bilgi)))) 2 3)))
      (setq row (1+ row))
      (setq i   (1+   i))
    )
  (vlax-invoke-method nwb  "SaveAs" fname -4143 nil nil :vlax-false :vlax-false 1 2)
  (vlax-invoke-method aexc "Quit" )
  (vlax-release-object cll)
  (vlax-release-object csht)
  (vlax-release-object sht)
  (vlax-release-object nwb)
  (vlax-release-object aexc)
  (gc)
  (gc)
  (gc)
  (gc)
  (alert (strcat "File saved as: " fname ))
(princ)
)
;--------------------------------------------------------------------------------------------------------------------------------------------------------
(setq source_path "c:/REN_QT/" )                                               ;
;--------------------------------------------------------------------------------------------------------------------------------------------------------
(defun c:RQTE ( / )
(vl-load-com)
(setq osmode_old (getvar "osmode"))
(setq dimzin_old (getvar "dimzin"))
(setq clayer_old (getvar "clayer"))
(setvar "cmdecho" 0 )
(setvar "osmode"  0 )
(setvar "dimzin"  1 )
(setvar "attreq"  0 )
(setq olcu_carp 0.001 ) ; ölçü mm dir.
(setq eset (ssget (list (cons 0 "INSERT") (cons 2  "RL-POS"))))
(if (= eset nil) (progn (terpri) (princ "\n No element selected...") (exit)))
(setq toplam_bilgi (RENAISSANCE_toplam_bilgi_olustur eset ))
(hata_kontrol toplam_bilgi)
(setq toplam_bilgi (RENAISSANCE_toplam_bilgi_derle toplam_bilgi ))
(setq cap_liste    (cap_bilgi_olustur  toplam_bilgi ))
(ren_metraj_tablo_dosya_yaz cap_liste toplam_bilgi )
(setvar "osmode" osmode_old)
(setvar "clayer" clayer_old)
(setvar "dimzin" dimzin_old)
(setvar "cmdecho" 1)
(princ)
)

;-------------------------------------------------------------------------------------------------------------------------------------------------------------------------------
