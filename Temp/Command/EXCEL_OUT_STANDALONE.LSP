;--------------------------------------------------------------------------------------------------------------------------------------------------------
;--------------------------------------------------------------------------------------------------------------------------------------------------------
;--------------------------------------------------------------------------------------------------------------------------------------------------------
;--------------------------------------------------------------------------------------------------------------------------------------------------------
;--------------------------------------------------------------------------------------------------------------------------------------------------------
(defun cp_ag ( cp / cp ) (* 0.00616537558266997 (* cp cp)))
;--------------------------------------------------------------------------------------------------------------------------------------------------------
(defun r_b_h (cap) (if (> cap 20) (* cap 3.5) (* cap 2.0)))
;--------------------------------------------------------------------------------------------------------------------------------------------------------
(defun m_b_h (cap) (if (> cap 20) (* cap 7.0) (* cap 4.0)))
;--------------------------------------------------------------------------------------------------------------------------------------------------------
(defun min_boy (boy / )
(setq boy_isle_2 (vl-string-translate "-~" "  " boy))
  (if (= boy boy_isle_2)
    (setq boy boy_isle_2)
    (setq boy (rtos (eval (read (strcat "(min " boy_isle_2 ")"))) 2 0))
  )
boy
)
;--------------------------------------------------------------------------------------------------------------------------------------------------------
(defun max_boy (boy / )
(setq boy_isle_2 (vl-string-translate "-~" "  " boy))
  (if (= boy boy_isle_2)
    (setq boy boy_isle_2)
    (setq boy (rtos (eval (read (strcat "(max " boy_isle_2 ")"))) 2 0))
  )
boy
)
;--------------------------------------------------------------------------------------------------------------------------------------------------------
(defun min_boy (boy / )
(setq boy_isle_2 (vl-string-translate "-~" "  " boy))
  (if (= boy boy_isle_2)
    (setq boy boy_isle_2)
    (setq boy (rtos (eval (read (strcat "(min " boy_isle_2 ")"))) 2 0))
  )
boy
)
;--------------------------------------------------------------------------------------------------------------------------------------------------------
(defun fi_ (/) (setq fi "%%C" ))
;--------------------------------------------------------------------------------------------------------------------------------------------------------
(defun boy_oku_isle (boy / )
(setq boy_isle_1 (vl-string-translate "lL=" "   " boy))
(setq boy_isle_2 (vl-string-translate "-~" "  " boy_isle_1))
  (if (= boy_isle_1 boy_isle_2)
    (setq boy boy_isle_1)
    (setq boy (rtos (eval (read (strcat "(* 0.5 (+ " boy_isle_2 "))"))) 2 2))
  )
boy
)
;--------------------------------------------------------------------------------------------------------------------------------------------------------
(defun boy_a_oku_isle (boy / )
(setq boy_isle_2 (vl-string-translate "-~" "  " boy))
  (if (= boy boy_isle_2)
    (setq boy boy_isle_2)
    (setq boy (rtos (eval (read (strcat "(* 0.5 (+ " boy_isle_2 "))"))) 2 0))
  )
boy
)
;--------------------------------------------------------------------------------------------------------------------------------------------------------
(defun adet_oku_isle (tb / )
(fi_)
(setq fi_boyu (strlen fi))
(setq fi_yeri (vl-string-search fi tb))
(setq adet_isle_1 (vl-string-translate "xX" "  " (substr tb 1 fi_yeri)))
  (if (= adet adet_isle_1)
    (setq adet adet_isle_1)
    (setq adet (rtos (eval (read (strcat "(* " adet_isle_1 ")"))) 2 0))
  )
adet
)
;--------------------------------------------------------------------------------------------------------------------------------------------------------
(defun cap_oku_isle (tb / )
(fi_)
(setq fi_boyu (strlen fi))
(setq tb_boyu (strlen tb))
(setq fi_yeri (vl-string-search fi   tb      ))
(setq b_yeri  (vl-string-search "/"  tb      ))
(if (= b_yeri nil) (setq b_yeri (+ 1 (strlen tb))))
(setq cap (substr tb (+ 1 fi_boyu fi_yeri)  (- b_yeri  fi_yeri fi_boyu)))
(setq cap (itoa (atoi cap)))
cap
)
;--------------------------------------------------------------------------------------------------------------------------------------------------------
(defun aralik_oku_isle (tb / )
(fi_)
(setq fi_boyu  (strlen fi))
(setq tb_boyu  (strlen tb))
(setq b_yeri   (vl-string-search "/"  tb      ))
(if (/= b_yeri nil)
        (setq aralik_b   (substr tb (+ 2 b_yeri )  (- tb_boyu b_yeri)))
        (setq aralik_b ""))
aralik_b
)
;--------------------------------------------------------------------------------------------------------------------------------------------------------
(defun a_oku (en tag /)
(vl-load-com)
(setq tag (strcase tag))
(setq deger "")
(setq blk  (vlax-ename->vla-object en))
(setq atts (vlax-invoke blk 'getattributes))
(foreach att atts
    (if (= tag (vla-get-tagstring att)) (setq deger (vla-get-textstring att)))
)
 deger
)
;--------------------------------------------------------------------------------------------------------------------------------------------------------
(defun cap_bilgi_olustur ( toplam_bilgi / )
(setq i 0)
(setq cap_liste (list))
(while(< i (length toplam_bilgi))
(setq cap  (cdr (nth  3 (nth i toplam_bilgi))))
(setq adet (cdr (nth  2 (nth i toplam_bilgi))))
(setq boy  (cdr (nth 14 (nth i toplam_bilgi))))
(setq toplam_boy (rtos (* (atof adet) boy ) 2 8))
(setq cap_ekle (list (cons 0 i ) (cons 1 cap) (cons 2 toplam_boy)))
(setq cap_liste (cons cap_ekle cap_liste))
(setq i (+ i 1))
)
(setq cap_liste (vl-sort cap_liste (function (lambda (e1 e2) (< (atoi (cdr (assoc 1 e1))) (atoi (cdr (assoc 1 e2))))))))
(setq i 0)
(setq bilgi_adet (length cap_liste))
(while(< i bilgi_adet)
(if (= (cdr (assoc 1 (nth i cap_liste))) (cdr (assoc 1 (nth (+ i 1) cap_liste))))
(progn
(setq adet_topla (rtos (+ (atof (cdr (assoc 2 (nth i cap_liste)))) (atof (cdr (assoc 2 (nth (+ i 1) cap_liste))))) 2 8))
(setq cap_liste  (subst (subst (cons 2 adet_topla) (assoc 2 (nth i cap_liste)) (nth i cap_liste)) (nth i cap_liste) cap_liste))
(setq cap_liste  (vl-remove (nth (+ i 1) cap_liste) cap_liste))
(setq bilgi_adet (- bilgi_adet 1))
(setq i (- i 1))
)
)
(setq i (+ i 1))
)
cap_liste
)
;--------------------------------------------------------------------------------------------------------------------------------------------------------
(defun RENAISSANCE_toplam_bilgi_olustur ( eset / )
(setq toplam_bilgi (list))
(setq cntr 0)
(while(< cntr (sslength eset))
(setq en (ssname eset cntr))
(setq grup_carpani (a_oku en "GC" ))
(if (= grup_carpani "") (setq grup_carpani "1"))
(setq gc_deger (atoi grup_carpani))
(setq ok_bilgi (list (cons  0  cntr  )
                     (cons  1 (a_oku en "POZ"))
                     (cons  2 (rtos (* gc_deger (atof (adet_oku_isle (a_oku en "TB" )))) 2 0 ))
                     (cons  3 (cap_oku_isle    (a_oku en "TB" )))
                     (cons  4 (aralik_oku_isle (a_oku en "TB" )))
                     (cons  5 (a_oku en "BOY" ))
                     (cons  6 (a_oku en "TIP" ))
                     (cons  7 (a_oku en "A"   ))
                     (cons  8 (a_oku en "B"   ))
                     (cons  9 (a_oku en "C"   ))
                     (cons 10 (a_oku en "D"   ))
                     (cons 11 (a_oku en "E"   ))
                     (cons 12 (a_oku en "F"   ))
                     (cons 13 (a_oku en "R"   ))
                     (cons 14 (atoi (boy_oku_isle (a_oku en "BOY" ))))
                     (cons 15 (a_oku en "MALZEME" ))

                                                                       ))

(setq toplam_bilgi (cons ok_bilgi toplam_bilgi))
(setq cntr(+ cntr 1))
)
(setq toplam_bilgi (vl-sort toplam_bilgi (function (lambda (e1 e2)      (< (atoi (cdr (assoc  1 e1))) (atoi (cdr (assoc  1 e2))))))))
(setq toplam_bilgi (vl-sort toplam_bilgi (function (lambda (e1 e2) (and (= (atoi (cdr (assoc  1 e1))) (atoi (cdr (assoc  1 e2))))
                                                                        (< (atoi (cdr (assoc  3 e1))) (atoi (cdr (assoc  3 e2)))))))))
(setq toplam_bilgi (vl-sort toplam_bilgi (function (lambda (e1 e2) (and (= (atoi (cdr (assoc  1 e1))) (atoi (cdr (assoc  1 e2))))
                                                                        (= (atoi (cdr (assoc  3 e1))) (atoi (cdr (assoc  3 e2))))
                                                                        (<       (cdr (assoc 14 e1))        (cdr (assoc 14 e2))))))))
toplam_bilgi
)
;--------------------------------------------------------------------------------------------------------------------------------------------------------
(defun RENAISSANCE_toplam_bilgi_derle ( toplam_bilgi / )
(setq i 0)
(setq bilgi_adet (length toplam_bilgi))
(while(< i bilgi_adet)
(if (and (= (cdr (assoc 1 (nth i toplam_bilgi))) (cdr (assoc 1 (nth (+ i 1) toplam_bilgi))))
         (= (cdr (assoc 3 (nth i toplam_bilgi))) (cdr (assoc 3 (nth (+ i 1) toplam_bilgi))))
         (= (cdr (assoc 5 (nth i toplam_bilgi))) (cdr (assoc 5 (nth (+ i 1) toplam_bilgi)))))
(progn
(setq adet_topla (itoa (+ (atoi (cdr (assoc 2 (nth i toplam_bilgi)))) (atoi (cdr (assoc 2 (nth (+ i 1) toplam_bilgi)))))))
(setq toplam_bilgi (subst (subst (cons 2 adet_topla) (assoc 2 (nth i toplam_bilgi)) (nth i toplam_bilgi)) (nth i toplam_bilgi) toplam_bilgi))
(setq toplam_bilgi (vl-remove (nth (+ i 1) toplam_bilgi) toplam_bilgi))
(setq bilgi_adet (- bilgi_adet 1))
(setq i (- i 1))
)
)
(setq i (+ i 1))
)
toplam_bilgi
)
;--------------------------------------------------------------------------------------------------------------------------------------------------------
(defun ren_metraj_tablo_dosya_yaz (cap_liste toplam_bilgi / en_son_toplam_agirlik anlik_tarih fname template_file cll csht rang sht nwb awb aexc)
(setq anlik_tarih (RTOS (GETVAR "CDATE") 2 6))
(setq fname (strcat (getvar "dwgprefix") (substr (getvar "dwgname") 1 (- (strlen (getvar "dwgname")) 4 )) "-" anlik_tarih ".xls"))
(setq aexc  (vlax-get-or-create-object "Excel.Application"))
(if (null aexc) (progn (alert "Excel baslatilamadi.") (exit)))
(setq  awb  (vlax-get-property  aexc "Workbooks" ))
(setq  nwb  (vlax-invoke-method awb  "Add"       ))
(setq  sht  (vlax-get-property  nwb  "Sheets"    ))
(setq  csht (vlax-get-property  sht  "Item" 1    ))
(setq  cll  (vlax-get-property  csht "Cells"     ))
(vla-put-visible aexc :vlax-false)
    (setq  row  9 ) ; Metrajýn eklenmeye baþlayacaðý satýr.
    (setq  row_num (length toplam_bilgi))
    (setq  i    0 )
      (vlax-put-property  cll "Item"   8  1 (vl-princ-to-string "Pos"   ))
      (vlax-put-property  cll "Item"   8  2 (vl-princ-to-string "Ø"     ))
      (vlax-put-property  cll "Item"   8  3 (vl-princ-to-string "Item"  ))
      (vlax-put-property  cll "Item"   8  4 (vl-princ-to-string "Length"))
    (repeat row_num
      (vlax-put-property  cll "Item" row  1 (vl-princ-to-string (cdr (assoc  1 (nth i toplam_bilgi)))))
      (vlax-put-property  cll "Item" row  2 (vl-princ-to-string (cdr (assoc  3 (nth i toplam_bilgi)))))
      (vlax-put-property  cll "Item" row  3 (vl-princ-to-string (cdr (assoc  2 (nth i toplam_bilgi)))))
      (vlax-put-property  cll "Item" row  4 (vl-princ-to-string (rtos (* olcu_carp (cdr (assoc 14 (nth i toplam_bilgi)))) 2 3)))
      (setq row (1+ row))
      (setq i   (1+   i))
    )
  (vlax-invoke-method nwb  "SaveAs" fname -4143 nil nil :vlax-false :vlax-false 1 2)
  (vlax-invoke-method aexc "Quit" )
  (vlax-release-object cll)
  (vlax-release-object csht)
  (vlax-release-object sht)
  (vlax-release-object nwb)
  (vlax-release-object aexc)
  (gc)
  (gc)
  (gc)
  (gc)
  (alert (strcat "File saved as: " fname ))
(princ)
)
;--------------------------------------------------------------------------------------------------------------------------------------------------------
(defun c:RQTE ( / )
(vl-load-com)
(setq osmode_old (getvar "osmode"))
(setq dimzin_old (getvar "dimzin"))
(setq clayer_old (getvar "clayer"))
(setvar "cmdecho" 0 )
(setvar "osmode"  0 )
(setvar "dimzin"  1 )
(setvar "attreq"  0 )
(setq olcu_carp 0.001 ) ; ölçü mm dir.
(setq eset (ssget (list (cons 0 "INSERT") (cons 2  "RL-POS"))))
(if (= eset nil) (progn (terpri) (princ "\n No element selected...") (exit)))
(setq toplam_bilgi (RENAISSANCE_toplam_bilgi_olustur eset ))
(setq toplam_bilgi (RENAISSANCE_toplam_bilgi_derle toplam_bilgi ))
(setq cap_liste    (cap_bilgi_olustur  toplam_bilgi ))
(ren_metraj_tablo_dosya_yaz cap_liste toplam_bilgi )
(setvar "osmode" osmode_old)
(setvar "clayer" clayer_old)
(setvar "dimzin" dimzin_old)
(setvar "cmdecho" 1)
(princ)
)

;-------------------------------------------------------------------------------------------------------------------------------------------------------------------------------
