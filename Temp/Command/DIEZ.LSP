;--------------------------------------------------------------------------------------------------------------------------------------------------------
(defun c:diez (/)
(SETQ HK (* 1000 (GETVAR "DIMSCALE")))
(setq i 0)
(setq pt1 nil)
(setq pozbul_eset (ssget "X" (list (cons 0 "INSERT") (cons -4  "<OR") (cons 2 "RL-POS") (cons 2 "RL-POS2") (cons -4  "OR>") )))
(setq toplam_adet 0)
  (while(< i (sslength pozbul_eset))
   (setq en (ssname pozbul_eset i))
   (setq poz_bul (strcat (a_oku en "POZ" )(a_oku en "TB")(a_oku en "A")(a_oku en "B")(a_oku en "C")(a_oku en "D")(a_oku en "E")(a_oku en "F")(a_oku en "R")))
   (if (/= (vl-string-search "#" poz_bul 0 ) nil)
        (progn
          (setq toplam_adet (+ toplam_adet 1))
         )
   )
   (setq i (+ i 1))
  )
(setq i 0)
(if (= toplam_adet 0)
 (Princ "\n Diez isaretli bir poz bulunmuyor...")
 (progn
  (setq pt3 (getpoint (strcat "\n" (itoa toplam_adet) ".Adet eleman bulundu. Bulunan pozlara simdi isaretleyeceginiz noktadan oklar cizilecek... Lutfen bu noktayi gosteriniz... ")))
  (while(< i (sslength pozbul_eset))
   (setq en (ssname pozbul_eset i))
   (setq poz_bul (strcat (a_oku en "POZ" )(a_oku en "TB")(a_oku en "A")(a_oku en "B")(a_oku en "C")(a_oku en "D")(a_oku en "E")(a_oku en "F")(a_oku en "R")))
   (if (/= (vl-string-search "#" poz_bul 0 ) nil)
        (progn
          (setq pt1 (cdr (assoc 10 (entget en))))
          (setq aci (angle pt1 pt3))
          (setq pt2 (polar pt1 aci (* hk  0.240) ) )
          (command "osmode" 0 "clayer" "ren.arrow" "pline" pt1 "w" 0 (* hk  0.080) pt2 "w" 0 0 pt3 "")
         )
   )
   (setq i (+ i 1))
  )
  )
)
(princ)
)
;--------------------------------------------------------------------------------------------------------------------------------------------------------
