;------------------------------------------------------------------------------;
;                     ARD ARDA SIRALI YAZI YAZAR                               ;
;------------------------------------------------------------------------------;
(defun ad_layer_liste_olustur ( / layer_adi)
(setq ad_layer_liste nil)
(setq ad_layer_bilgi (tblnext "layer" T))
  (while (/= ad_layer_bilgi nil)
    (setq layer_adi  (cdr (assoc  2 ad_layer_bilgi )))
    (setq ad_layer_liste (cons layer_adi ad_layer_liste))
    (setq ad_layer_bilgi (tblnext "layer" ))
  )
    (setq ad_layer_liste (acad_strlsort  ad_layer_liste))
)
;------------------------------------------------------------------------------;
(defun ad_hazir_yazi_liste ( / )
(setq ad_liste nil)
(setq dosya_adi (strcat source_pathlisp"Ayar/HAZIR_YAZI.txt"))
(setq dosya (open dosya_adi "r"))
(setq ad_yazi_liste_oku  (read-line dosya))
 (while (/= ad_yazi_liste_oku nil)
   (setq ad_liste (cons ad_yazi_liste_oku ad_liste))
   (setq ad_yazi_liste_oku  (read-line dosya))
 )
    (close dosya)
    (setq ad_hazir_liste (reverse ad_liste))
)
;------------------------------------------------------------------------------;
(defun ad_ayarlari_dosyaya_yaz (/)
(setq dosya (open (strcat client_path "Standard/ad.txt") "w"))
(princ (get_tile  "ad_basla_sayi"        ) dosya ) (princ "\n" dosya)
(princ (get_tile  "ad_yazi_on_ek"        ) dosya ) (princ "\n" dosya)
(princ (get_tile  "ad_yazi_arka_ek"      ) dosya ) (princ "\n" dosya)
(princ (get_tile  "ad_yazi_hane_adet"    ) dosya ) (princ "\n" dosya)
(princ (get_tile  "ad_yeni_yazi_yaz"     ) dosya ) (princ "\n" dosya)
(princ (get_tile  "ad_ekle_yazi_degis"   ) dosya ) (princ "\n" dosya)
(princ (get_tile  "ad_ekle_yazi_on_ek"   ) dosya ) (princ "\n" dosya)
(princ (get_tile  "ad_ekle_yazi_arka_ek" ) dosya ) (princ "\n" dosya)
(princ (get_tile  "ad_layer_mevcut"      ) dosya ) (princ "\n" dosya)
(princ (get_tile  "ad_layer_degis"       ) dosya ) (princ "\n" dosya)
(princ (get_tile  "ad_yeni_layer_adi"    ) dosya ) (princ "\n" dosya)
(princ (get_tile  "ad_yeni_yazi_yuk"     ) dosya ) (princ "\n" dosya)
(princ (get_tile  "ad_yeni_yazi_aci"     ) dosya ) (princ "\n" dosya)
(princ (get_tile  "ad_sayi_grubu_iptal"  ) dosya ) (princ "\n" dosya)
(princ (get_tile  "ad_hazir_yazi"        ) dosya ) (princ "\n" dosya)
(princ (get_tile  "ad_attribute_tag"     ) dosya ) (princ "\n" dosya)
(close dosya)
)
;-------------------------------------------------------------------------------
(defun ad_ayarlari_dosyaya_yaz2 (/)
(setq dosya (open (strcat client_path "Standard/ad.txt") "w"))
(princ ad_basla_sayi        dosya ) (princ "\n" dosya)
(princ ad_yazi_on_ek        dosya ) (princ "\n" dosya)
(princ ad_yazi_arka_ek      dosya ) (princ "\n" dosya)
(princ ad_yazi_hane_adet    dosya ) (princ "\n" dosya)
(princ ad_yeni_yazi_yaz     dosya ) (princ "\n" dosya)
(princ ad_ekle_yazi_degis   dosya ) (princ "\n" dosya)
(princ ad_ekle_yazi_on_ek   dosya ) (princ "\n" dosya)
(princ ad_ekle_yazi_arka_ek dosya ) (princ "\n" dosya)
(princ ad_layer_mevcut      dosya ) (princ "\n" dosya)
(princ ad_layer_degis       dosya ) (princ "\n" dosya)
(princ ad_yeni_layer_adi    dosya ) (princ "\n" dosya)
(princ ad_yeni_yazi_yuk     dosya ) (princ "\n" dosya)
(princ ad_yeni_yazi_aci     dosya ) (princ "\n" dosya)
(princ ad_sayi_grubu_iptal  dosya ) (princ "\n" dosya)
(princ ad_hazir_yazi        dosya ) (princ "\n" dosya)
(princ ad_attribute_tag     dosya ) (princ "\n" dosya)
(close dosya)
)
;-------------------------------------------------------------------------------
(defun ad_ayarlari_dosyadan_oku (/)
 (if (= (not (open (strcat client_path "Standard/ad.txt") "r")) t )
 (progn (setq dosya (open (strcat client_path "Standard/ad.txt") "w"))
 (princ "1" dosya )(princ "\n" dosya)
 (princ "A" dosya )(princ "\n" dosya)
 (princ "A" dosya )(princ "\n" dosya)
 (princ "1" dosya )(princ "\n" dosya)
 (princ "0" dosya )(princ "\n" dosya)
 (princ "1" dosya )(princ "\n" dosya)
 (princ "0" dosya )(princ "\n" dosya)
 (princ "0" dosya )(princ "\n" dosya)
 (princ "1" dosya )(princ "\n" dosya)
 (princ "0" dosya )(princ "\n" dosya)
 (princ "0" dosya )(princ "\n" dosya)
 (princ "20" dosya )(princ "\n" dosya)
 (princ "0" dosya )(princ "\n" dosya)
 (princ "0" dosya )(princ "\n" dosya)
 (princ "0" dosya )(princ "\n" dosya)
 (princ "\n" dosya)
 (close dosya)))

(setq dosya (open (strcat client_path "Standard/ad.txt") "r"))
(setq ad_basla_sayi         (read-line dosya)  )
(setq ad_yazi_on_ek         (read-line dosya)  )
(setq ad_yazi_arka_ek       (read-line dosya)  )
(setq ad_yazi_hane_adet     (read-line dosya)  )
(setq ad_yeni_yazi_yaz      (read-line dosya)  )
(setq ad_ekle_yazi_degis    (read-line dosya)  )
(setq ad_ekle_yazi_on_ek    (read-line dosya)  )
(setq ad_ekle_yazi_arka_ek  (read-line dosya)  )
(setq ad_layer_mevcut       (read-line dosya)  )
(setq ad_layer_degis        (read-line dosya)  )
(setq ad_yeni_layer_adi     (read-line dosya)  )
(setq ad_yeni_yazi_yuk      (read-line dosya)  )
(setq ad_yeni_yazi_aci      (read-line dosya)  )
(setq ad_sayi_grubu_iptal   (read-line dosya)  )
(setq ad_hazir_yazi         (read-line dosya)  )
(setq ad_attribute_tag      (read-line dosya)  )
(close dosya)
)
;-------------------------------------------------------------------------------
(defun ad_yazi_basla (/)
(ad_layer_liste_olustur)
(start_list "ad_yeni_layer_adi") (mapcar 'add_list ad_layer_liste) (end_list)
(ad_ayarlari_dosyadan_oku)
(ad_hazir_yazi_liste)
(start_list "ad_hazir_yazi")     (mapcar 'add_list ad_hazir_liste) (end_list)
(set_tile  "ad_basla_sayi"        ad_basla_sayi        )
(set_tile  "ad_yazi_on_ek"        ad_yazi_on_ek        )
(set_tile  "ad_yazi_arka_ek"      ad_yazi_arka_ek      )
(set_tile  "ad_yazi_hane_adet"    ad_yazi_hane_adet    )
(set_tile  "ad_yeni_yazi_yaz"     ad_yeni_yazi_yaz     )
(set_tile  "ad_ekle_yazi_degis"   ad_ekle_yazi_degis   )
(set_tile  "ad_ekle_yazi_on_ek"   ad_ekle_yazi_on_ek   )
(set_tile  "ad_ekle_yazi_arka_ek" ad_ekle_yazi_arka_ek )
(set_tile  "ad_layer_mevcut"      ad_layer_mevcut      )
(set_tile  "ad_layer_degis"       ad_layer_degis       )
(set_tile  "ad_yeni_layer_adi"    ad_yeni_layer_adi    )
(set_tile  "ad_yeni_yazi_yuk"     ad_yeni_yazi_yuk     )
(set_tile  "ad_yeni_yazi_aci"     ad_yeni_yazi_aci     )
(set_tile  "ad_sayi_grubu_iptal"  ad_sayi_grubu_iptal  )
(set_tile  "ad_hazir_yazi"        ad_hazir_yazi        )
(set_tile  "ad_attribute_tag"     ad_attribute_tag     )
(if (= ad_layer_mevcut  "1") (mode_tile "ad_yeni_layer_adi" 1 ))
(if (= ad_layer_degis   "1") (mode_tile "ad_yeni_layer_adi" 0 ))
(if (= ad_yeni_yazi_yaz "1")
(progn (mode_tile "ad_yeni_yazi_yuk" 0 )(mode_tile "ad_yeni_yazi_aci" 0 ))
(progn (mode_tile "ad_yeni_yazi_yuk" 1 )(mode_tile "ad_yeni_yazi_aci" 1 )))
(if (= ad_sayi_grubu_iptal "1")
   (progn
      (mode_tile  "ad_basla_sayi"     1 )
      (mode_tile  "ad_yazi_arka_ek"   1 )
      (mode_tile  "ad_yazi_hane_adet" 1 )
      (mode_tile  "ad_hazir_yazi"     0 )
   )
   (progn
      (mode_tile  "ad_basla_sayi"     0 )
      (mode_tile  "ad_yazi_arka_ek"   0 )
      (mode_tile  "ad_yazi_hane_adet" 0 )
      (mode_tile  "ad_hazir_yazi"     1 )
   )
)
)
;-------------------------------------------------------------------------------
(defun ad_basla_sayi_act        ( / )
(ad_ayarlari_dosyaya_yaz)
)
;-------------------------------------------------------------------------------
(defun ad_basla_sayi_0_act      ( / )
(set_tile  "ad_basla_sayi"     "1"  )
(ad_ayarlari_dosyaya_yaz)
)
;-------------------------------------------------------------------------------
(defun ad_yazi_on_ek_act        ( / )
(ad_ayarlari_dosyaya_yaz)
)
;-------------------------------------------------------------------------------
(defun ad_yazi_on_ek_al_act     ( / )
(ad_ayarlari_dosyaya_yaz)
(done_dialog 5)
)
;-------------------------------------------------------------------------------
(defun ad_yazi_on_ek_al_action ( / )
(ad_ayarlari_dosyadan_oku)
(setq b_en (car (entsel "\n Bir text seçiniz... ")))
(if (and (/= b_en nil) (= (cdr (assoc 0 (entget b_en))) "TEXT")) (setq ad_yazi_on_ek (cdr (assoc 1 (entget b_en)))))
(ad_ayarlari_dosyaya_yaz2)
)
;-------------------------------------------------------------------------------
(defun ad_yazi_arka_ek_act      ( / )
(ad_ayarlari_dosyaya_yaz)
)
;-------------------------------------------------------------------------------
(defun ad_yazi_arka_ek_al_act     ( / )
(ad_ayarlari_dosyaya_yaz)
(done_dialog 6)
)
;-------------------------------------------------------------------------------
(defun ad_yazi_arka_ek_al_action ( / )
(ad_ayarlari_dosyadan_oku)
(setq b_en (car (entsel "\n Bir text seçiniz... ")))
(if (and (/= b_en nil) (= (cdr (assoc 0 (entget b_en))) "TEXT")) (setq ad_yazi_arka_ek (cdr (assoc 1 (entget b_en)))))
(ad_ayarlari_dosyaya_yaz2)
)
;-------------------------------------------------------------------------------
(defun ad_yazi_hane_adet_act    ( / )
(ad_ayarlari_dosyaya_yaz)
)
;-------------------------------------------------------------------------------
(defun ad_yeni_yazi_yaz_act     ( / )
(set_tile "ad_ekle_yazi_degis"   "0")
(set_tile "ad_ekle_yazi_on_ek"   "0")
(set_tile "ad_ekle_yazi_arka_ek" "0")
(mode_tile  "ad_yeni_yazi_yuk"    0 )
(mode_tile  "ad_yeni_yazi_aci"    0 )
(ad_ayarlari_dosyaya_yaz)
)
;-------------------------------------------------------------------------------
(defun ad_ekle_yazi_degis_act   ( / )
(set_tile "ad_yeni_yazi_yaz"     "0")
(set_tile "ad_ekle_yazi_on_ek"   "0")
(set_tile "ad_ekle_yazi_arka_ek" "0")
(mode_tile  "ad_yeni_yazi_yuk"    1 )
(mode_tile  "ad_yeni_yazi_aci"    1 )
(ad_ayarlari_dosyaya_yaz)
)
;-------------------------------------------------------------------------------
(defun ad_ekle_yazi_on_ek_act   ( / )
(set_tile "ad_yeni_yazi_yaz"     "0")
(set_tile "ad_ekle_yazi_degis"   "0")
(set_tile "ad_ekle_yazi_arka_ek" "0")
(mode_tile  "ad_yeni_yazi_yuk"    1 )
(mode_tile  "ad_yeni_yazi_aci"    1 )
(ad_ayarlari_dosyaya_yaz)
)
;-------------------------------------------------------------------------------
(defun ad_ekle_yazi_arka_ek_act ( / )
(set_tile "ad_yeni_yazi_yaz"     "0")
(set_tile "ad_ekle_yazi_degis"   "0")
(set_tile "ad_ekle_yazi_on_ek"   "0")
(mode_tile  "ad_yeni_yazi_yuk"    1 )
(mode_tile  "ad_yeni_yazi_aci"    1 )
(ad_ayarlari_dosyaya_yaz)
)
;-------------------------------------------------------------------------------
(defun ad_layer_mevcut_act      ( / )
(set_tile  "ad_layer_degis"      "0")
(mode_tile "ad_yeni_layer_adi"    1 )
(ad_ayarlari_dosyaya_yaz)
)
;-------------------------------------------------------------------------------
(defun ad_layer_degis_act       ( / )
(set_tile   "ad_layer_mevcut"    "0")
(mode_tile  "ad_yeni_layer_adi"   0 )
(ad_ayarlari_dosyaya_yaz)
)
;-------------------------------------------------------------------------------
(defun ad_yeni_layer_adi_act    ( / )
(ad_ayarlari_dosyaya_yaz)
)
;-------------------------------------------------------------------------------
(defun ad_yeni_yazi_yuk_act     ( / )
(ad_ayarlari_dosyaya_yaz)
)
;-------------------------------------------------------------------------------
(defun ad_yeni_yazi_aci_act     ( / )
(ad_ayarlari_dosyaya_yaz)
)
;-------------------------------------------------------------------------------
(defun ad_attribute_tag_act     ( / )
(ad_ayarlari_dosyaya_yaz)
)
;-------------------------------------------------------------------------------
(defun ad_ciz_act               ( / )
(ad_ayarlari_dosyaya_yaz)
(done_dialog 4)
)
;-------------------------------------------------------------------------------
(defun ad_sayi_grubu_iptal_act  ( / )
(if (= (get_tile "ad_sayi_grubu_iptal") "1")
   (progn
      (mode_tile  "ad_basla_sayi"     1 )
      (mode_tile  "ad_yazi_arka_ek"   1 )
      (mode_tile  "ad_yazi_hane_adet" 1 )
      (mode_tile  "ad_hazir_yazi"     0 )
   )
   (progn
      (mode_tile  "ad_basla_sayi"     0 )
      (mode_tile  "ad_yazi_arka_ek"   0 )
      (mode_tile  "ad_yazi_hane_adet" 0 )
      (mode_tile  "ad_hazir_yazi"     1 )
   )
)
(ad_ayarlari_dosyaya_yaz)
)
;-------------------------------------------------------------------------------
(defun son_yazi (on_ek sayi arka_ek / )
(while (and (/= (atoi sayi) 0) (< (strlen sayi) (atoi ad_yazi_hane_adet))) (setq sayi (strcat "0" sayi)))
(while (and ( = (atoi sayi) 0) (< (strlen sayi) (atoi ad_yazi_hane_adet))) (setq sayi (strcat "A" sayi)))
(if (= ad_sayi_grubu_iptal "1" ) (progn (setq sayi "") (setq arka_ek "")))
(strcat on_ek sayi arka_ek)
)
;-------------------------------------------------------------------------------
(defun ad_hazir_yazi_act        ( / )
(set_tile "ad_yazi_on_ek" (nth (atoi (get_tile "ad_hazir_yazi")) ad_hazir_liste))
(ad_ayarlari_dosyaya_yaz)
)
;-------------------------------------------------------------------------------
(defun sayi_arttir (sayi / )
(setq sayi (strcase sayi))
(if (and (> (strlen sayi) 0) (= (atoi sayi) 0))
      (progn
         (if (> (strlen sayi) 1)
             (progn
                (setq sayi_on_bolum (substr sayi 1 (- (strlen sayi) 1)))
                (setq sayi (substr sayi (strlen sayi) 1))
             )
                (setq sayi_on_bolum "")
         )
         (setq sayi (strcat (substr sayi 1 (- (strlen sayi) 1)) (chr (+ 1 (ascii (substr sayi (strlen sayi) 1))))))
      )
         (setq sayi (itoa (+ 1 (atoi sayi))))
)
sayi
)
;-------------------------------------------------------------------------------
(defun ad_yazi                  ( / )
(ad_layer_liste_olustur)
(ad_ayarlari_dosyadan_oku)
(setq yaz_yuk (atof ad_yeni_yazi_yuk))
(setq yaz_aci (atof ad_yeni_yazi_aci))
(setq ad_basla_sayi (strcase ad_basla_sayi))
(setq sayi ad_basla_sayi)
(if (= ad_yeni_yazi_yaz "1")
(progn
(setq Yerlesim (GetPoint  "\n Yerlesim noktasi..."))
   (while (/= Yerlesim nil)
        (setq clayer_old   (getvar "clayer"  ))
         (if (= ad_layer_degis "1")
           (setvar "clayer" (nth (atoi ad_yeni_layer_adi) ad_layer_liste))
         )
        (setq yeni_yazi (son_yazi ad_yazi_on_ek sayi ad_yazi_arka_ek))
        (command "text" "bc" Yerlesim yaz_yuk yaz_aci yeni_yazi)
        (setvar "clayer"   clayer_old   )
        (setq Yerlesim (GetPoint "\n Yerlesim noktasi..."))
        (setq sayi (sayi_arttir sayi))
      )
))
(if (/= ad_yeni_yazi_yaz "1")
(progn
(if (= ad_layer_mevcut "1") (setq layer_yeni nill))
(if (= ad_layer_degis  "1") (setq layer_yeni (nth (atoi ad_yeni_layer_adi) ad_layer_liste)))
  (setq yazi_eski_ent (ssget ":S" (list (cons -4  "<OR") (cons 0 "TEXT")  (cons 0 "INSERT")  (cons -4  "OR>") )))
  (while (/= yazi_eski_ent nil)
      (if (= (cdr (assoc 0 (entget (ssname yazi_eski_ent 0)))) "TEXT")
           (progn
             (setq yeni_yazi (son_yazi ad_yazi_on_ek sayi ad_yazi_arka_ek))
             (setq yazi_eski_ (entget (ssname yazi_eski_ent 0)))
             (if (= ad_ekle_yazi_degis   "1") (setq yazi_eski_ (SUBST (CONS 1 yeni_yazi)   (ASSOC 1 yazi_eski_) yazi_eski_)))
             (if (= ad_ekle_yazi_on_ek   "1") (setq yazi_eski_ (SUBST (CONS 1 (strcat yeni_yazi "" (cdr (assoc 1 yazi_eski_))))(ASSOC 1 yazi_eski_) yazi_eski_ )))
             (if (= ad_ekle_yazi_arka_ek "1") (setq yazi_eski_ (SUBST (CONS 1 (strcat (cdr (assoc 1 yazi_eski_)) "" yeni_yazi))(ASSOC 1 yazi_eski_) yazi_eski_ )))
             (if (/= layer_yeni nill)         (setq yazi_eski_ (SUBST (CONS 8 layer_yeni)  (ASSOC 8 yazi_eski_) yazi_eski_)))
             (ENTMOD yazi_eski_)
           )
      )
      (if (= (cdr (assoc 0 (entget (ssname yazi_eski_ent 0)))) "INSERT")
           (progn
             (setq ad_attribute_tag (strcase ad_attribute_tag))
             (setq yeni_yazi (son_yazi ad_yazi_on_ek sayi ad_yazi_arka_ek))
             (setq yazi_eski (a_oku (ssname yazi_eski_ent 0) ad_attribute_tag))
             (if (= ad_ekle_yazi_degis   "1")  (att_yaz (ssname yazi_eski_ent 0) ad_attribute_tag         yeni_yazi            ))
             (if (= ad_ekle_yazi_on_ek   "1")  (att_yaz (ssname yazi_eski_ent 0) ad_attribute_tag (strcat yeni_yazi yazi_eski )))
             (if (= ad_ekle_yazi_arka_ek "1")  (att_yaz (ssname yazi_eski_ent 0) ad_attribute_tag (strcat yazi_eski yeni_yazi )))
           )
      )
     (setq sayi (sayi_arttir sayi))
     (setq yazi_eski_ent (ssget ":S" (list (cons -4  "<OR") (cons 0 "TEXT")  (cons 0 "INSERT")  (cons -4  "OR>") )))
  )
))
(ad_ayarlari_dosyadan_oku)
(setq ad_basla_sayi sayi)
(ad_ayarlari_dosyaya_yaz2)
(princ)
)
;-------------------------------------------------------------------------------
(defun c:sd ( / )
(setvar "cmdecho" 0)
        (setq id (load_dialog (strcat source_pathlisp"Lisp/Sayi Sirala.dcl")))
        (if (not (new_dialog "ad_dialog" id))(exit))
           (action_tile "ad_basla_sayi"        "(ad_basla_sayi_act)"        )
           (action_tile "ad_basla_sayi_0"      "(ad_basla_sayi_0_act)"      )
           (action_tile "ad_yazi_on_ek"        "(ad_yazi_on_ek_act)"        )
           (action_tile "ad_yazi_on_ek_al"     "(ad_yazi_on_ek_al_act)"     )
           (action_tile "ad_yazi_arka_ek"      "(ad_yazi_arka_ek_act)"      )
           (action_tile "ad_yazi_arka_ek_al"   "(ad_yazi_arka_ek_al_act)"   )
           (action_tile "ad_yazi_hane_adet"    "(ad_yazi_hane_adet_act)"    )
           (action_tile "ad_yeni_yazi_yaz"     "(ad_yeni_yazi_yaz_act)"     )
           (action_tile "ad_yeni_yazi_yuk"     "(ad_yeni_yazi_yuk_act)"     )
           (action_tile "ad_yeni_yazi_aci"     "(ad_yeni_yazi_aci_act)"     )
           (action_tile "ad_ekle_yazi_degis"   "(ad_ekle_yazi_degis_act)"   )
           (action_tile "ad_ekle_yazi_on_ek"   "(ad_ekle_yazi_on_ek_act)"   )
           (action_tile "ad_ekle_yazi_arka_ek" "(ad_ekle_yazi_arka_ek_act)" )
           (action_tile "ad_layer_mevcut"      "(ad_layer_mevcut_act)"      )
           (action_tile "ad_layer_degis"       "(ad_layer_degis_act)"       )
           (action_tile "ad_yeni_layer_adi"    "(ad_yeni_layer_adi_act)"    )
           (action_tile "ad_sayi_grubu_iptal"  "(ad_sayi_grubu_iptal_act)"  )
           (action_tile "ad_hazir_yazi"        "(ad_hazir_yazi_act)"        )
           (action_tile "ad_attribute_tag"     "(ad_attribute_tag_act)"     )
           (action_tile "ad_ciz"               "(ad_ciz_act)"               )
           (action_tile "ad_cik"               "(done_dialog)  (exit)"      )
           (action_tile "cancel"               "(done_dialog)  (exit)"      )
      (ad_yazi_basla)
    (setq dialog-state (start_dialog))
 (if (= dialog-state 4) (ad_yazi))
 (if (= dialog-state 5) (progn (ad_yazi_on_ek_al_action)   (c:sd)))
 (if (= dialog-state 6) (progn (ad_yazi_arka_ek_al_action) (c:sd)))
(setvar "cmdecho" 1)
)
;------------------------------------------------------------------------------;
