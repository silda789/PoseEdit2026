(defun c:PAFTA ( / okunan)
(setvar "cmdecho" 0)
(if (= (getvar "ATTREQ") 1) (setvar "ATTREQ" 0))
(setq pt1 (getpoint "\n Yerleştirilecek Nokta.....:"))
(command "-insert" (strcat source_pathlisp"Pafta Antetleri/PaftaCercevesi") pt1 1 "" 0 )
(command "_.explode" (entlast))
(command "-insert" (strcat source_pathlisp"Pafta Antetleri/"(PROJE_OKU)) pt1 1 "" 0 )
(command "_.explode" (entlast))
(if (= (getvar "ATTREQ") 0) (setvar "ATTREQ" 1))
(princ)
)
(defun c:CERCEVE (/)
(setvar "cmdecho" 0)
(if (= (getvar "ATTREQ") 1) (setvar "ATTREQ" 0))
(setq pt1 (getpoint "\n Yerleştirilecek Nokta.....:"))
(command "-insert" (strcat source_pathlisp"Pafta Antetleri/PaftaCercevesi") pt1 1 "" 0 )
(command "_.explode" (entlast))
(if (= (getvar "ATTREQ") 0) (setvar "ATTREQ" 1))
(princ)
)
