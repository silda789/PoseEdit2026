; ------------------------------------------------------------------------------------
; --- SECILEN BIR CIZGI GRUBU ICIN BOYLARI VE TOPLAM BOYU YAZAR ----------------------
; ------------------------------------------------------------------------------------
;*******************************************************************************
(defun boy_ort_yaz (p1 p2 yazyuk yaz konum oteleme kacma)
(setq aci    (angle     p1 p2 ))
(if (and (> aci (* pi 0.50)) (<= aci (* pi 1.505))  )
  (progn
     (setq aci (+ aci pi))
     (setq p_gec p1 )
     (setq p1 p2)
     (setq p2 p_gec)
     )
  )
(setq mesafe (* 0.50 (distance  p1 p2 )))
(setq p3 (polar p1 aci (+ mesafe oteleme)))
(if (and (> aci (* pi 0.51)) (<= aci (* pi 1.51)))   (setq aci (+ aci pi)))
(setq p4 (polar p3 (+ aci (* 0.5 pi)) kacma ))
(setq p5 (polar p3 (- aci (* 0.5 pi)) kacma ))
(if (= konum "U")(command "text" "j" "mc"  p4 yazyuk (/ (* aci 180 ) pi ) yaz)
                 (command "text" "j" "mc"  p5 yazyuk (/ (* aci 180 ) pi ) yaz)))
;*******************************************************************************
(defun c:bo ( / aci       b         n         l         bb
                baskor    sonkor    boy       orta      pt1
                yazi      top_boy   n1        yuk       olcekk
                boyyazisi yaz_yuk   yaz_olc   gecici           )
(TERPRI)
(setq blipmode_old (getvar "blipmode"))
(setq cmdecho_old  (getvar "cmdecho" ))
(setq clayer_old   (getvar "clayer"  ))
(setq luprec_old   (getvar "luprec"  ))
(setq osmode_old   (getvar "osmode"  ))
(setq dimzin_old   (getvar "dimzin"  ))
;(setvar "dimzin"   1 )
(SETQ OL (* 0.01 (OLCEK_OKU)))
(SETQ yaz_olc      (GETVAR "DIMLFAC" ))
(SETQ HASSAS       (GETVAR "DIMDEC"  ))
(if (= (BIRIM_OKU) 1000 ) (setq SAYI_2 10) (setq SAYI_2 1))
(SETQ SAYI         (EXPT 10 HASSAS))
(setq yaz_yuk      (* 300 ol ))
(setq kacma        (* 1 ol ))
(command "clayer" "ren.text")
(setvar   "osmode" 0)
(setvar   "TEXTSTYLE" "ren Gost.common" )
(command  "luprec" "8")
(PRINC    "Cizgi seç...   ")
(setq top_boy 0)
(if (= dnt_boyu nil)  (progn  (setq dnt_boyu 1) (setq hassas   0)))
(if (= dnt_boyu 1)
          (princ "Donatý için ölçülendirme...")
          (princ "Normal ölçülendirme..."))
(setq B (ssget))
(if (= B nil)
     (progn
          (if (= dnt_boyu 1)
               (progn
                    (setq dnt_boyu 0)
                    (princ "Normal ölçülendirme...")
               )
               (progn
                    (setq dnt_boyu 1)
                    (setq hassas   0)
                    (princ "Donatý için ölçülendirme...")
               )
          )
          (setq B (ssget))
     )
)
(setq N (SSLENGTH B))
(setq L 0)
(setq buyuk 0)
(WHILE (< L N)
(setq BB (ENTGET (SSNAME B L)))
(if (= "LINE" (CDR (ASSOC 0 BB)))
      (PROGN
       (setq baskor    (cdr (assoc 10 bb)))
       (setq sonkor    (cdr (assoc 11 bb)))
       (setq boy  (* yaz_olc (distance baskor sonkor)))
              (if (> boy buyuk)(progn (setq buyuk boy) (setq p1 baskor) (setq p2 sonkor)))
(if  (= dnt_boyu 0)
       (setq boy     (float (* (fix (+ (/ BOY SAYI   ) 0.50 )) SAYI   )))
       (setq boy     (float (* (fix (+ (/ BOY SAYI_2 ) 0.50 )) SAYI_2 )))
)
       (setvar "luprec"  HASSAS)
       (setq yazi (rtos boy 2 HASSAS))
       (boy_ort_yaz baskor sonkor yaz_yuk yazi "A" 0 (* 1.25 yaz_yuk))
      )
)
(if (= "LWPOLYLINE" (CDR (ASSOC 0 BB)))
    (progn
       (setq k 0 ptlist nil h_list nil)
       (repeat (length bb)
         (setq bb_en (nth k bb))
         (if (= (car bb_en) 10) (setq ptlist (append ptlist (list (cdr bb_en)))))
         (if (= (car bb_en) 42) (setq h_list (append h_list (list (cdr bb_en)))))
         (setq k (1+ k))
        )
        (setq npt (length ptlist))
        (setq llist nil k 0 pboyA 0)
        (repeat (1- npt)
        (if (= (nth k h_list) 0)
           (setq boy  (* yaz_olc (distance (nth k ptlist) (nth (1+ k) ptlist))))
          (progn
             (setq s_value (distance (nth k ptlist) (nth (1+ k) ptlist)))
             (setq h_value (* (* 0.5 s_value) (nth k h_list)))
             (setq r_value (+ (* 0.5 h_value)  (/ (* s_value s_value) (* 8 h_value))))
             (setq a_value (* 4 (atan (nth k h_list))))
             (setq boy (* yaz_olc (* r_value a_value)))
             (princ)
          )
        )
           (if  (= dnt_boyu 0)
            (setq boy (float (* (fix (+ (/ BOY SAYI   ) 0.50 )) SAYI   )))
            (setq boy (float (* (fix (+ (/ BOY SAYI_2 ) 0.50 )) SAYI_2 )))
           )
           (setvar "luprec"  HASSAS)
           (setq yazi (rtos boy 2 HASSAS))
          (boy_ort_yaz (nth k ptlist) (nth (1+ k) ptlist) yaz_yuk yazi "A" 0 (* 1.25 yaz_yuk))
          (setq k (1+ k))
        )
    )
)
;   (setq top_boy (+ top_boy boy))
   (setq L (+ L 1))
)

;
; (setq yazi_duzelt_sec (entsel "\n Yazý düzelt eleman ..." ))
; (if (/= yazi_duzelt_sec nil)
;           (progn
;              (setq dmt_duzelt  (entget (car yazi_duzelt_sec)))
;              (setq yazi_tuzelt (strcat (substr (cdr (assoc 1 dmt_duzelt)) 1 (- (strlen (cdr (assoc 1 dmt_duzelt))) (strlen (rtos top_boy 2 0)))) (rtos top_boy 2 0)))
;              (setq dmt_duzelt  (SUBST (CONS 1 yazi_tuzelt) (ASSOC 1 dmt_duzelt) dmt_duzelt))
;              (ENTMOD dmt_duzelt)
;           )
;           (progn
;              (layer_e_gec "DN_BOYL" "5" "")
;              (setq boyyazisi (strcat "L=" (rtos top_boy 2 HASSAS)))
;              (boy_ort_yaz p1 p2 (* 1.25 yaz_yuk) boyyazisi "U" (* -5 yaz_yuk) (* 1.25 yaz_yuk))
;           )
; )
(setvar "blipmode" blipmode_old )
(setvar "cmdecho"  cmdecho_old  )
(setvar "clayer"   clayer_old   )
(setvar "luprec"   luprec_old   )
(setvar "osmode"   osmode_old   )
(setvar "dimzin"   dimzin_old   )
(princ)
)
;*******************************************************************************
