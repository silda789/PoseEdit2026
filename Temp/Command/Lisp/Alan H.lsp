(defun alan_yazi (pt1 text height)
  (entmake (list (cons 0 "TEXT")
		 (cons 100 "AcDbEntity")
		 (cons 100 "AcDbText")
		 (cons   7 "R")
		 (cons  10  pt1)
		 (cons  11  pt1)
		 (cons   1  text)
		 (cons  40  height)
		 (cons  50  0)
		 (cons  41  0.75)
		 (cons  72  1)
		 (cons  73  2)
		 (cons   8 "0")
           )
  )
(princ)
)
; -----------------------------------------------------------------------------------------
; --- ALAN VE CEVRE HESAPLAR --------------------------------------------------------------
; -----------------------------------------------------------------------------------------
(defun alan_hesap ( p  / )
(setvar "cmdecho"  0)
(setq toplam_alan 0.0)
(setq l 0 n (sslength p))
    (if (/= p nil)
      (progn
        (while (< l n)
            (command "area" "o" (ssname p l))
            (setq alan  (getvar "area"     ))
            (setq toplam_alan  (+ toplam_alan   alan))
            (setq l (+ l 1))
        )
      )
    )
toplam_alan
)
; -----------------------------------------------------------------------------------------
(defun cevre_hesap ( p / )
(setvar "cmdecho"  0)
(setq toplam_cevre 0.0)
(setq l 0 n (sslength p))
    (if (/= p nil)
      (progn
        (while (< l n)
            (command "area" "o" (ssname p l))
            (setq cevre (getvar "perimeter"))
            (setq toplam_cevre (+ toplam_cevre cevre))
            (setq l (+ l 1))
        )
      )
    )
toplam_cevre
)
; -----------------------------------------------------------------------------------------
(defun c:a ( / toplam_alan toplam_cevre p l n alan cevre yazi_1 yazi_2)
(setq dimzin_old (getvar "dimzin"))
(setvar "dimzin" 1)
(setq osmode_old (getvar "osmode"  ))
(SETQ k1 (GETVAR "DIMSCALE"))
(SETQ k2 (GETVAR "DIMLFAC"))
(setq yaz_yuk   (* 25 k2) )
(setq olc_carp (BIRIM_OKU))
(setq p (ssget))
(setq toplam_alan  (alan_hesap  p))
(setq toplam_cevre (cevre_hesap p))
(alert (setq sp1 (strcat "Alan: " (rtos (/ (* toplam_alan  (* k2 k2 )) (* olc_carp olc_carp) ) 2 2) " m2   Cevre: " (rtos (/ (* toplam_cevre k2 )  olc_carp) 2 2) " mt") ;_strcat
		 ) ;_setq
	  ) ;_alert
	  (princ sp1)
(setvar "osmode" osmode_old)
(setvar "dimzin" dimzin_old)
)
; ------------------------------- PROGRAM SONU --------------------------------------------
(defun c:aaaa ()
(alert (strcat "RQT        : Metraj tablosunu cizime ekler \nEE         : Poz degistirmek veya olusturmak icin \nPZREDEF    : Mevcut pozlari gunceller. \nRECHANGE   : Eski pozlar? yeni sisteme getirir. \ntik0       : Tik bilgisini topluca 0 yapar. \ntbac       : 77 ile al?nm?? bilgilerin toplam bilgilerini a?ar \npozclayer  : T?m pozlar?n layerlar?n? d?zeltir. \npzg        : T?m a??l?m bloklar?n? redefine eder \ntdd0       : T?m se?ilen pozlar?n pozisyonlar?n? de?i?tirir. \ntdd1       : T?m se?ilen pozlar?n pozisyonlar?n? de?i?tirir. \ntdd2       : T?m se?ilen pozlar?n pozisyonlar?n? de?i?tirir.
" )

))

; ------------------------------- PROGRAM SONU --------------------------------------------
(defun c:ay ( / toplam_alan toplam_cevre p l n alan cevre yazi_1 yazi_2)
(setq dimzin_old (getvar "dimzin"))
(setvar "dimzin" 1)
(setq osmode_old (getvar "osmode"  ))
(SETQ k1 (GETVAR "DIMSCALE"))
(SETQ k2 (GETVAR "DIMLFAC"))
(setq olc_carp (BIRIM_OKU))
(setq yaz_yuk   (* 2.5  k2) )
(princ "\n Genel alan......:")
(setq p_set1 (ssget))
(setq alan1  (alan_hesap  p_set1))
(setq cevre1 (cevre_hesap p_set1))
(princ "\n Çýkarýlacak alan......:")
(setq p_set2 (ssget))
(setq alan2  (alan_hesap  p_set2))
(setq cevre2 (cevre_hesap p_set2))
(setq yazi_1   (strcat "A: "  (rtos (/ (- alan1   alan2 ) (* 10 olc_carp) ) 2 2)  " m² " ))
(setq yazi_2   (strcat "C: "  (rtos (/ (+ cevre1 cevre2 )    olc_carp           ) 2 2)  " mt " ))
(setq pt1 (getpoint "\nYerlesim noktasý..."))
(setvar "osmode"   0)
(if (/= pt1 nil) (progn (alan_yazi pt1 yazi_1 yaz_yuk)
                        (setq pt1 (polar pt1 (* pi 1.5) (* 1.5 yaz_yuk)))
                        (alan_yazi pt1 yazi_2 yaz_yuk)))
(setvar "osmode" osmode_old)
(setvar "dimzin" dimzin_old)
(princ)
)
; ------------------------------- PROGRAM SONU --------------------------------------------
