(defun c:Key (/)
(setvar "cmdecho" 0)
(if (= (getvar "ATTREQ") 1) (setvar "ATTREQ" 0))
(setq pt1 (getpoint "\n Yerleştirilecek Nokta.....:"))
(command "-insert" (strcat source_pathlisp"Pafta Antetleri/Key_"(PROJE_OKU)) pt1 1 "" 0 )
(command "_.explode" (entlast))
(if (= (getvar "ATTREQ") 0) (setvar "ATTREQ" 1))
(princ)
)
