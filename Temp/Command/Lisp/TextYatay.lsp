(defun c:y (/)
(setq B (ssget '((-4 . "<OR") (0 . "TEXT") (0 . "MTEXT") (0 . "INSERT")  (0 . "ATTDEF") (-4 . "OR>") )))
(setq N (sslength B))
(setq L 0)
(setq yeni_aci 0)
(while (< L N)
(setq PT1        (cdr (ASSOC 10 (ENTGET (SSNAME B L)))))
(setq MEVCUT_ACI (cdr (ASSOC 50 (ENTGET (SSNAME B L)))))
(setq MEVCUT_ACI (/ (* MEVCUT_ACI 180) PI))
(SETQ DONDUR_ACI (- yeni_aci MEVCUT_ACI ))
(setq osmode_old   (getvar "osmode"  ))
(setvar "osmode"   0)
(command "_rotate" (SSNAME B L) "" PT1 DONDUR_ACI)
(setvar "osmode"   osmode_old   )
(setq L (+ L 1))
)
)
;;;;;;;;;;;;;;
(defun c:yy (/)
(setq B (ssget '((-4 . "<OR") (0 . "TEXT") (0 . "MTEXT") (0 . "INSERT")  (0 . "ATTDEF") (-4 . "OR>") )))
(setq N (sslength B))
(setq L 0)
(setq yeni_aci 90)
(while (< L N)
(setq PT1        (cdr (ASSOC 10 (ENTGET (SSNAME B L)))))
(setq MEVCUT_ACI (cdr (ASSOC 50 (ENTGET (SSNAME B L)))))
(setq MEVCUT_ACI (/ (* MEVCUT_ACI 180) PI))
(SETQ DONDUR_ACI (- yeni_aci MEVCUT_ACI ))
(setq osmode_old   (getvar "osmode"  ))
(setvar "osmode"   0)
(command "_rotate" (SSNAME B L) "" PT1 DONDUR_ACI)
(setvar "osmode"   osmode_old   )
(setq L (+ L 1))
)
)
