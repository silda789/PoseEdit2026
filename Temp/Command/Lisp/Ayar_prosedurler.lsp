;;;;;;;;;Attribute okumalari icin kullanilir;;;;;;;;;;;;;;;;;
(defun a_oku (en tag /)
(vl-load-com)
(setq tag (strcase tag))
(setq deger "")
(setq blk  (vlax-ename->vla-object en))
(setq atts (vlax-invoke blk 'getattributes))
(foreach att atts
    (if (= tag (vla-get-tagstring  att)) (setq deger (vla-get-textstring att)))
)
 deger
)
;Genel prosedürler (birden çok programda kullanılır)
;-----------------------------------------------------------------------
;-----------------------------------------------------------------------
(defun layer_yap ( layer_name color line_type /  layer_name color line_type)

  (if (= (tblsearch "layer" layer_name) nil)
      (progn
      (command "-layer" "new" layer_name  "" )
      (command "-layer" "l" line_type layer_name "c" color layer_name  "" )
      )
      )
)
;-----------------------------------------------------------------------
(defun tan (aci / aci) (/ (sin aci) (cos aci)) )
;-----------------------------------------------------------------------
(defun yaz ( yazi / yazi )(princ "\n")(princ yazi)(princ "\n"))
;-----------------------------------------------------------------------
(defun rtod (a)   (/ (* a 180.0) pi) )
;-----------------------------------------------------------------------
(defun dtor (a)   (* (/ a 180  ) pi) )
;-----------------------------------------------------------------------
(defun midpoint (P1 P2) (polar  P1 (angle P1 P2) (/ (distance P1 P2) 2.0)) )
;-----------------------------------------------------------------------
(defun StrPos (s1 s2 / l1 l2 i n )
   (setq i 1 l1 (strlen s1) l2 (strlen s2) n 0)
   (while (<= i l2)
          (if (= (substr s2 i l1) s1)
              (setq n i i l2)
          )
          (setq i (1+ i))
   )
   (setq i n)
)
;-----------------------------------------------------------------------
(defun rtoa (a i j / s)
   (setq s (rtos a i j))
   (if (/= (StrPos "." s) 0)
       (progn
          (while (and (> j 0) (= (substr s (strlen s) 1) "0"))
                 (setq j (1- j) s (substr s 1 (1- (strlen s))))
          )
          (if (= (substr s (strlen s) 1) ".")
              (setq s (substr s 1 (1- (strlen s))))
          )
       )
   )
   (setq s s)
)
;-----------------------------------------------------------------------
(defun deger_degistir ( dosya sira deger / dosya sira deger okunan isim i liste)
(setq isim  (strcat source_pathlisp"Ayar/" dosya)  )
(setq takas (strcat source_pathlisp"Ayar/temp.txt"))

    (setq dosya_oku (open isim  "r"))
     (setq dosya_yaz (open takas "w"))
         (setq okunan (read-line dosya_oku))
               (while (/= okunan nil)
                  (princ okunan dosya_yaz) (princ "\n" dosya_yaz)
                  (setq  okunan (read-line dosya_oku))
               )
     (close dosya_yaz)
    (close dosya_oku)
(setq i 1)
    (setq dosya_yaz (open takas "r"))
     (setq dosya_oku (open isim  "w"))
         (setq okunan (read-line dosya_yaz))
               (while (/= okunan nil)
                  (if (= sira i)
                         (progn (princ deger  dosya_oku) (princ "\n" dosya_oku))
                         (progn (princ okunan dosya_oku) (princ "\n" dosya_oku))
                   )
                  (setq i (+ i 1))
                  (setq  okunan (read-line dosya_yaz))
               )
     (close dosya_oku)
    (close dosya_yaz)
(princ)
)
;-----------------------------------------------------------------------
(defun deger_ekle ( dosya sira deger / dosya sira deger okunan isim i liste)
;(setq isim  (strcat "c:\\depo\\lsp\\ayar\\" dosya)  )
(setq isim   dosya )
(setq takas (strcat source_pathlisp"Ayar/temp.txt"))

    (setq dosya_oku (open isim  "r"))
     (setq dosya_yaz (open takas "w"))
         (setq okunan (read-line dosya_oku))
               (while (/= okunan nil)
                  (princ okunan dosya_yaz) (princ "\n" dosya_yaz)
                  (setq  okunan (read-line dosya_oku))
               )
     (close dosya_yaz)
    (close dosya_oku)
(setq i 1)
    (setq dosya_yaz (open takas "r"))
     (setq dosya_oku (open isim  "w"))
         (setq okunan (read-line dosya_yaz))
               (while (/= okunan nil)
                  (if (= sira i)
                         (progn (princ deger  dosya_oku) (princ "\n" dosya_oku))
                   )
                         (progn (princ okunan dosya_oku) (princ "\n" dosya_oku))
                  (setq i (+ i 1))
                  (setq  okunan (read-line dosya_yaz))
               )
     (close dosya_oku)
    (close dosya_yaz)
(princ)
)
;-----------------------------------------------------------------------
;-----------------------------------------------------------------------
(defun deger_cikar ( dosya sira / dosya sira okunan isim i liste)
;(setq isim  (strcat "c:\\depo\\lsp\\ayar\\" dosya)  )
(setq isim   dosya )
(setq takas (strcat source_pathlisp"Ayar/temp.txt"))

    (setq dosya_oku (open isim  "r"))
     (setq dosya_yaz (open takas "w"))
         (setq okunan (read-line dosya_oku))
               (while (/= okunan nil)
                  (princ okunan dosya_yaz) (princ "\n" dosya_yaz)
                  (setq  okunan (read-line dosya_oku))
               )
     (close dosya_yaz)
    (close dosya_oku)
(setq i 1)
    (setq dosya_yaz (open takas "r"))
     (setq dosya_oku (open isim  "w"))
         (setq okunan (read-line dosya_yaz))
               (while (/= okunan nil)
                  (if (/= sira i)
                         (progn (princ okunan dosya_oku) (princ "\n" dosya_oku))
                   )
                  (setq i (+ i 1))
                  (setq  okunan (read-line dosya_yaz))
               )
     (close dosya_oku)
    (close dosya_yaz)
(princ)
)
;-----------------------------------------------------------------------
(defun  kod_degis  (
                     entiti_list
                     new_feature
                     list_no
                                    /  entiti_list new_feature list_no old_feature
                    )
(setq old_feature (cdr (assoc list_no entiti_list)))
(setq entiti_list (subst (cons list_no new_feature) (assoc list_no entiti_list) entiti_list))
(entmod entiti_list)
(princ)
)
;-----------------------------------------------------------------------
(defun liste_yap (dosya / dosya okunan dosya_oku)
(setq dosya_oku (open dosya  "r"))
(setq liste nil)
    (setq okunan (read-line dosya_oku))
               (while (/= okunan nil)
                  (setq liste  (cons okunan liste  ))
                  (setq okunan (read-line dosya_oku))
               )
    (setq liste (reverse liste))
 (close dosya_oku)
)
;---------------------------------------------------------------------------------
(defun once (/)
(setq blipmode_old (getvar "blipmode"))
(setq cmdecho_old  (getvar "cmdecho" ))
(setq clayer_old   (getvar "clayer"  ))
(setq luprec_old   (getvar "luprec"  ))
(setq osmode_old   (getvar "osmode"  ))
)
;----
(defun sonra (/)
(setvar "blipmode" blipmode_old )
(setvar "cmdecho"  cmdecho_old  )
(setvar "clayer"   clayer_old   )
(setvar "luprec"   luprec_old   )
(setvar "osmode"   osmode_old   )
)
;---------------------------------------------------------------------------------
(defun donut_center (donut / )
(setq k 0 ptlist nil)
  (repeat (length donut)
    (setq bb_en (nth k donut))
    (if (= (car bb_en) 10) (setq ptlist (append ptlist (list (cdr bb_en)))))
    (setq k (1+ k))
  )
(setq pn (polar (car ptlist) (angle (car ptlist) (cadr ptlist)) (/ (distance (car ptlist) (cadr ptlist)) 2.0)))
pn
)
;---------------------------------------------------------------------------------


(defun c:CX   ( )
(command "ZOOM" "E")
(command "audit" "y" )
(command "purge" "a" "*" "n")
(command "qsave")
(command "_close")
)
