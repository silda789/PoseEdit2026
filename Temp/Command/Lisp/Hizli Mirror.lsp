;   X Yönünde   ;
(defun c:hm ()
(setq blipmode_old (getvar "blipmode"))
(setq cmdecho_old  (getvar "cmdecho" ))
(setq clayer_old   (getvar "clayer"  ))
(setq luprec_old   (getvar "luprec"  ))
(setq osmode_old   (getvar "osmode"  ))
(setq grup (ssget))
(setvar "mirrtext"   0 )
(setvar "osmode"   691 )
(setq pt1 (getpoint "\n Mirror merkezi"))
(setvar "osmode"   0)
(command "mirror" grup "" (polar pt1 (* 0.5 pi) 1000) (polar pt1 (* 1.5 pi) 1000) "y")
(setvar "blipmode" blipmode_old )
(setvar "cmdecho"  cmdecho_old  )
(setvar "clayer"   clayer_old   )
(setvar "luprec"   luprec_old   )
(setvar "osmode"   osmode_old   )
)

;   Y Yönünde   ;
(defun c:hmm ()
(setq blipmode_old (getvar "blipmode"))
(setq cmdecho_old  (getvar "cmdecho" ))
(setq clayer_old   (getvar "clayer"  ))
(setq luprec_old   (getvar "luprec"  ))
(setq osmode_old   (getvar "osmode"  ))
(setq grup (ssget))
(setvar "mirrtext"   0 )
(setvar "osmode"   691 )
(setq pt1 (getpoint "\n Mirror merkezi"))
(setvar "osmode"   0)
(command "mirror" grup "" (polar pt1 0 1000) (polar pt1 pi 1000) "y")
(setvar "blipmode" blipmode_old )
(setvar "cmdecho"  cmdecho_old  )
(setvar "clayer"   clayer_old   )
(setvar "luprec"   luprec_old   )
(setvar "osmode"   osmode_old   )
)
;;;;;;;;;;;;;
;   X Yönünde   ;
(defun c:jm ()
(setq blipmode_old (getvar "blipmode"))
(setq cmdecho_old  (getvar "cmdecho" ))
(setq clayer_old   (getvar "clayer"  ))
(setq luprec_old   (getvar "luprec"  ))
(setq osmode_old   (getvar "osmode"  ))
(setq grup (ssget))
(setvar "mirrtext"   0 )
(setvar "osmode"   691 )
(setq pt1 (getpoint "\n Mirror merkezi"))
(setvar "osmode"   0)
(command "mirror" grup "" (polar pt1 (* 0.5 pi) 1000) (polar pt1 (* 1.5 pi) 1000) "n")
(setvar "blipmode" blipmode_old )
(setvar "cmdecho"  cmdecho_old  )
(setvar "clayer"   clayer_old   )
(setvar "luprec"   luprec_old   )
(setvar "osmode"   osmode_old   )
)

;   Y Yönünde   ;
(defun c:jmm ()
(setq blipmode_old (getvar "blipmode"))
(setq cmdecho_old  (getvar "cmdecho" ))
(setq clayer_old   (getvar "clayer"  ))
(setq luprec_old   (getvar "luprec"  ))
(setq osmode_old   (getvar "osmode"  ))
(setq grup (ssget))
(setvar "mirrtext"   0 )
(setvar "osmode"   691 )
(setq pt1 (getpoint "\n Mirror merkezi"))
(setvar "osmode"   0)
(command "mirror" grup "" (polar pt1 0 1000) (polar pt1 pi 1000) "n")
(setvar "blipmode" blipmode_old )
(setvar "cmdecho"  cmdecho_old  )
(setvar "clayer"   clayer_old   )
(setvar "luprec"   luprec_old   )
(setvar "osmode"   osmode_old   )
)
