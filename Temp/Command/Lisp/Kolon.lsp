(defun REN_Yaziyaz (pt1 text height yon1 mesafe1 yon2 mesafe2 D_72 D_73 / pt1 text height D_72 D_73)
;(setq pt1 (polar pt1 yon1 mesafe1 ))
;(setq pt1 (polar pt1 yon2 mesafe2 ))
(entmake (list (cons 0 "TEXT")
		  (cons 100 "AcDbEntity")
		  (cons 100 "AcDbText")
		  (cons   7 "ren Gost.common")
		  (cons  10 pt1)
		  (cons  11 pt1)
		  (cons   1 text)
		  (cons  40 height)
		  (cons  50 0)  ; rotation
		  (cons  41 0.80)
 		  (cons  72 D_72)
		  (cons  73 D_73)
		  (cons   8 "ren.mtr.layer_t1")
         )
)
(princ)
)



(defun ldeg (ldeg1 / ldeg1)
(command "change" (entlast) "" "p" "la" ldeg1  ""))
(defun yonler ()
(setq sag 0)
(setq sol pi)
(setq yukari (* 0.5 pi))
(setq asagi  (* 1.5 pi)))

(defun c:kolon ()
(if (null (tblsearch "dimstyle" "ren_25"))
    (progn
          (alert (strcat "\nLutfen ren_25 ve ren.detay_25 isimli Olcu Sistemini olusturunuz")))
    (progn
          (command "._-dimstyle" "_restore" "ren_25")))
(setq dc (getreal "\nAna Donati Capini Giriniz: "))
(setq ec (getreal "\nEtriye Capini Giriniz: "))
(setq pp (getreal "\nPaspayini Giriniz: "))
(setq ud (getreal "\nUst Kisimda Ortadaki Donati Adedini Giriniz:" ))
(setq yd (getreal "\nYan Kisimda Ortadaki Donati Adedini Giriniz:" ))
(setq boy1 (getreal "\nKolonun Boyunu Giriniz: "))
(setq boy2 (getreal "\nKolonun Enini Giriniz: "))
(setq nk1 (getpoint "\n Nokta Seciniz: "))
(kolonkesiticiz dc ec pp ud yd boy1 boy2 nk1)
)

(defun donut_koy (koyulacak_nokta1 koyulacak_nokta2 / koyulacak_nokta1 koyulacak_nokta2)	
           (entmake (list
					     (cons 0 "LWPOLYLINE")
					     (cons 100 "AcDbEntity")
					     (cons 410 "Model")
					     (cons 8 "ren.reinforcement")
					     (cons 100 "AcDbPolyline")
					     (cons 90 2)
					     (cons 70 1)
					     (cons 43 (* 0.5 dc))
					     (cons 10 koyulacak_nokta1)
					     (cons 40 0)
					     (cons 41 0)
					     (cons 42 1.0)
					     (cons 10 koyulacak_nokta2)
					     (cons 40 0)
					     (cons 41 0)
					     (cons 42 1.0))))

(defun kolonkesiticiz (dc ec pp ud yd boy1 boy2 nk1 / dc ec pp ud yd boy1 boy2 nk1)
(yonler)
(setq ol (GETVAR "DIMSCALE"))
(setq osmode_old   (getvar "osmode"  ))
(setvar "osmode" 0)
(setvar "attreq"  0 )
(setq nk2 (polar nk1 sag boy1))
(setq nk3 (polar nk2 asagi boy2))
(setq nk4 (polar nk3 sol boy1))
(entmake (list
         (cons 0 "LWPOLYLINE")(cons 100 "AcDbEntity")(cons 410 "Model")(cons 8 "ren.view")(cons 100 "AcDbPolyline")(cons 90 5)(cons 70 0)(cons 43 0)(cons 10 nk1)(cons 40 0)(cons 41 0)(cons 42 0)
         (cons 10 nk2)(cons 40 0)(cons 41 0)(cons 42 0)(cons 10 nk3)(cons 40 0)(cons 41 0)(cons 42 0)(cons 10 nk4)(cons 40 0)(cons 41 0)(cons 42 0)(cons 10 nk1)(cons 40 0)(cons 41 0)(cons 42 0) ))


(setq nk5 (polar nk1 (* pi 1.75) (sqrt (* 2 (* (+ pp (/ ec 2) (/ dc 2)) (+ pp (/ ec 2) (/ dc 2)))))))
(setq nk7 (polar nk5 sol (+ (/ ec 2) (/ dc 2))))
(setq nk6 (polar nk5 yukari (+ (/ ec 2) (/ dc 2))))


(setq nk8 (polar nk2 (* pi 1.25) (sqrt (* 2 (* (+ pp (/ ec 2) (/ dc 2)) (+ pp (/ ec 2) (/ dc 2)))))))
(setq nk9 (polar nk8 sag (+ (/ ec 2) (/ dc 2))))
(setq nk10 (polar nk8 yukari (+ (/ ec 2) (/ dc 2))))


(setq nk11 (polar nk3 (* pi 0.75) (sqrt (* 2 (* (+ pp (/ ec 2) (/ dc 2)) (+ pp (/ ec 2) (/ dc 2)))))))
(setq nk12 (polar nk11 sag (+ (/ ec 2) (/ dc 2))))
(setq nk13 (polar nk11 asagi (+ (/ ec 2) (/ dc 2))))


(setq nk14 (polar nk4 (* pi 0.25) (sqrt (* 2 (* (+ pp (/ ec 2) (/ dc 2)) (+ pp (/ ec 2) (/ dc 2)))))))
(setq nk15 (polar nk14 sol (+ (/ ec 2) (/ dc 2))))
(setq nk16 (polar nk14 asagi (+ (/ ec 2) (/ dc 2))))

(command "pline" nk15 nk7 "a" nk6 "l" nk10 "a" nk9 "l" nk12 "a" nk13 "l" nk16 "a" nk15 "")
(ldeg "ren.reinforcement" )


           (setq dn1 (polar nk5 sol (/ dc 4)))
	       (setq p1 (list (car dn1) (cadr dn1)))
	       (setq dn2 (polar nk5 sag (/ dc 4)))
	       (setq p2 (list (car dn2) (cadr dn2)))
	       (setq dn3 (polar nk5 (* pi 1.75) dc))
	       (command "circle" dn3 (/ dc 2))
           (ldeg "ren.reinforcement" )
           (donut_koy dn1 dn2)

           (setq dn1 (polar nk8 sol (/ dc 4)))
	       (setq p1 (list (car dn1) (cadr dn1)))
	       (setq dn2 (polar nk8 sag (/ dc 4)))
	       (setq p2 (list (car dn2) (cadr dn2)))
	       (setq dn3 (polar nk8 (* pi 1.25) dc))
	       (command "circle" dn3 (/ dc 2))
	       (ldeg "ren.reinforcement" )
           (donut_koy dn1 dn2)

           (setq dn1 (polar nk11 sol (/ dc 4)))
	       (setq p1 (list (car dn1) (cadr dn1)))
	       (setq dn2 (polar nk11 sag (/ dc 4)))
	       (setq p2 (list (car dn2) (cadr dn2)))
	       (setq dn3 (polar nk11 (* pi 0.75) dc))
	       (command "circle" dn3 (/ dc 2))
           (ldeg "ren.reinforcement" )
           (donut_koy dn1 dn2)

           (setq dn1 (polar nk14 sol (/ dc 4)))
	       (setq p1 (list (car dn1) (cadr dn1)))
	       (setq dn2 (polar nk14 sag (/ dc 4)))
	       (setq p2 (list (car dn2) (cadr dn2)))
	       (setq dn3 (polar nk14 (* pi 0.25) dc))
	       (command "circle" dn3 (/ dc 2))	
           (ldeg "ren.reinforcement" )
           (donut_koy dn1 dn2)
	
;;;Yatay kisim;;;					
(if (= ud 0)
         (progn  (command "dimlinear" nk1 nk5 "h" (polar nk1 yukari 100))
                 (ldeg "ren.dimension" )
                 (command "dimlinear" nk5 nk8 "h" (polar nk1 yukari 100))
                 (ldeg "ren.dimension" )
                 (command "dimlinear" nk8 nk2 "h" (polar nk1 yukari 100))
                 (ldeg "ren.dimension" )
                 (command "dimlinear" nk1 nk2 "h" (polar nk1 yukari 225))
                 (ldeg "ren.dimension" )
         )
(progn
(setq mes1 (distance nk5 nk8))
(setq ara1 (/ mes1 (+ ud 1)))
(setq nokta (polar nk5 sag ara1))
(setq noktaol nokta)
(setq noktaolc (polar nk5 sag ara1))
(setq noktaolcu noktaolc)
(command "dimlinear" nk5 noktaol (polar nk1 yukari 100))
(ldeg "ren.dimension" )
(setq aa 0)
(setq aa1 0)
(while (< aa ud)
  (setq r11 dc)
  (command "donut" 0 r11 nokta "" )
  (ldeg "ren.reinforcement" )
  (setq noktac (polar nokta asagi dc))
  (command "circle" noktac (/ dc 2))
  (setq nokta (polar nokta sag ara1))
  (ldeg "ren.reinforcement" )
  (command "dimlinear" noktaol nokta (polar nk1 (* 0.5 pi) 100))
  (ldeg "ren.dimension" )
  (setq noktaol (polar noktaol sag ara1))
  (setq aa (+ aa 1))
)
(command "dimlinear" nk1 nk5 (polar nk1 yukari 100))
(ldeg "ren.dimension" )
(command "dimlinear" nk2 nk8 (polar nk1 yukari 100))
(ldeg "ren.dimension" )
(command "dimlinear" nk1 nk2 (polar nk1 yukari 225))
(ldeg "ren.dimension" )
(setq mes1 (distance nk14 nk11))
(setq ara1 (/ mes1 (+ ud 1)))
(setq nokta (polar nk14 sag ara1))
(setq aa 0)
(while (< aa ud)
  (setq r11 dc)
  (command "donut" 0 r11 nokta "" )
  (ldeg "ren.reinforcement" )
  (setq noktac (polar nokta yukari dc))
  (command "circle" noktac (/ dc 2))
  (setq nokta (polar nokta sag ara1))
  (ldeg "ren.reinforcement" )
  (setq aa (+ aa 1))
)))
;;;Yatay kisim;;;
;;;dusey kisim;;;
(if (= yd 0)
         (progn  (command "dimlinear" nk4 nk16 "v" (polar nk1 sol 100))
                 (ldeg "ren.dimension" )
                 (command "dimlinear" nk16 nk6 "v" (polar nk1 sol 100))
                 (ldeg "ren.dimension" )
                 (command "dimlinear" nk6 nk1 "v" (polar nk1 sol 100))
                 (ldeg "ren.dimension" )
                 (command "dimlinear" nk4 nk1 "v" (polar nk1 sol 225))
                 (ldeg "ren.dimension" )
         )
(progn
(setq mes2 (distance nk5 nk14))
(setq ara2 (/ mes2 (+ yd 1)))
(setq nokta (polar nk5 asagi ara2))
(setq noktaol nokta)
(command "dimlinear" nk5 noktaol "v" (polar nk1 sol 100))
(ldeg "ren.dimension" )
(setq aa 0)
(while (< aa yd)
  (setq r11 dc)
  (command "donut" 0 r11 nokta "" )
  (ldeg "ren.reinforcement" )
  (setq noktac (polar nokta sag dc))
  (command "circle" noktac (/ dc 2))
  (setq nokta (polar nokta asagi ara2))
  (ldeg "ren.reinforcement" )
  (command "dimlinear" noktaol nokta "v" (polar nk1 sol 100))
  (ldeg "ren.dimension" )
  (setq noktaol (polar noktaol asagi ara2))
  (setq aa (+ aa 1))
)
(command "dimlinear" nk1 nk5 "v" (polar nk1 sol 100))
(ldeg "ren.dimension" )
(command "dimlinear" nk4 nk14 "v" (polar nk1 sol 100))
(ldeg "ren.dimension" )
(command "dimlinear" nk1 nk4 "v" (polar nk1 sol 225))
(ldeg "ren.dimension" )
(setq mes1 (distance nk8 nk11))
(setq ara2 (/ mes1 (+ yd 1)))
(setq nokta (polar nk8 asagi ara2))
(setq aa 0)
(while (< aa yd)
  (setq r11 dc)
  (command "donut" 0 r11 nokta "" )
  (ldeg "ren.reinforcement" )
  (setq noktac (polar nokta sol dc))
  (command "circle" noktac (/ dc 2))
  (setq nokta (polar nokta asagi ara2))
  (ldeg "ren.reinforcement" )
  (setq aa (+ aa 1))
)))
;;;Dusey kisim;;;
;;;Paspayi olcusu;;;

(command "dimlinear" nk3 nk13 "v" (polar nk3 sag 125))
(ldeg "ren.dimension" )
(command "dimlinear" nk3 nk12  (polar nk3 asagi 125))
(ldeg "ren.dimension" )


;;;Paspayi olcusu;;;
(setq nk17 (polar nk1 0 (/ 2 (distance nk1 nk2))))
(setq nk18 (polar nk17 yukari 450 ))
(REN_Yaziyaz nk18 "----" 75 sag 1000 asagi 0 1 2)

;;;Donati Metraji;;;

(setq ok1-1 (polar nk9 asagi (/ ara2 2)))
(setq ok1-2 (polar ok1-1 (* pi 1.85) 150))
(setq ok1-3 (polar ok1-2 sag 150))
(command "leader" ok1-1 ok1-2 ok1-3 "" "" "N")
(ldeg "ren.arrow" )

(setq ok2-1 (polar nk2 sag 50))
(setq ok2-2 (polar ok2-1 sag 150))
(command "leader" nk8 ok2-1 ok2-2 "" "" "N")
(ldeg "ren.arrow" )



;(setq ok4 (polar nk13 sol (/ ara1 2)))
;(setq ok5 (polar ok4 asagi 240))
;(setq ok6 (polar ok5 sol 650))
;(command "leader" ok4 ok5 ok6 "" "" "N")
;(ldeg "ren.arrow" )


;;;Donati Metraji;;;

;;;Ic Etriyeler;;;
(setq mes1 (distance nk5 nk8))
(setq mes2 (distance nk5 nk14))
(if (= ud 0)
         (progn  (setq poi poi)
         )
(progn
(setq dnt1 (entget (car (entsel "\n IcEtriye Atilacak 1. Donatiyi Yatay Yonde Ilk Once Soldakini Seciniz..."))))
(setq dnt2 (entget (car (entsel "\n IcEtriye Atilacak 2. Donatiyi Yatay Yonde Daha Donra Sagdakini Seciniz..."))))

(setq n1 (donut_center dnt1))
(setq n11 (polar n1 sol (+ (/ ec 2) (/ dc 2))))
(setq n12 (polar n1 yukari (+ (/ ec 2) (/ dc 2))))
(setq n2 (donut_center dnt2))
(setq n21 (polar n2 sag (+ (/ ec 2) (/ dc 2))))
(setq n22 (polar n2 yukari (+ (/ ec 2) (/ dc 2))))
(setq n5 (polar n1 asagi mes2))
(setq n51 (polar n5 sol (+ (/ ec 2) (/ dc 2))))
(setq n52 (polar n5 asagi (+ (/ ec 2) (/ dc 2))))
(setq n6 (polar n2 asagi mes2))
(setq n61 (polar n6 sag (+ (/ ec 2) (/ dc 2))))
(setq n62 (polar n6 asagi (+ (/ ec 2) (/ dc 2))))
(command "pline" n11 "a" n12 "l" n22 "a" n21 "l" n61 "a" n62 "l" n52 "a" n51 "l" n11 "")
(ldeg "ren.reinforcement" )
)
)
(if (= yd 0)
         (progn  (setq poi poi)
         )
(progn
(setq dnt3 (entget (car (entsel "\n IcEtriye Atilacak 1. Donatiyi Dusey Yonde Ilk Once Usttekikini Seciniz..."))))
(setq dnt4 (entget (car (entsel "\n IcEtriye Atilacak 2. Donatiyi Dusey Yonde Daha Donra Alttakini Seciniz..."))))
(setq n3 (donut_center dnt3))
(setq n31 (polar n3 sol (+ (/ ec 2) (/ dc 2))))
(setq n32 (polar n3 yukari (+ (/ ec 2) (/ dc 2))))
(setq n4 (donut_center dnt4))
(setq n41 (polar n4 sol (+ (/ ec 2) (/ dc 2))))
(setq n42 (polar n4 asagi (+ (/ ec 2) (/ dc 2))))
(setq n7 (polar n3 sag mes1))
(setq n71 (polar n7 sag (+ (/ ec 2) (/ dc 2))))
(setq n72 (polar n7 yukari (+ (/ ec 2) (/ dc 2))))
(setq n8 (polar n4 sag mes1))
(setq n81 (polar n8 sag (+ (/ ec 2) (/ dc 2))))
(setq n82 (polar n8 asagi (+ (/ ec 2) (/ dc 2))))
(command "pline" n31 "a" n32 "l" n72 "a" n71 "l" n81 "a" n82 "l" n42 "a" n41 "l" n31 "")
(ldeg "ren.reinforcement" )
))
;;;Ic Etriyeler;;;
(setvar "osmode"   osmode_old   )
)
