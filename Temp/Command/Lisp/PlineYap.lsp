(defun c:pee (/)
(SETQ GROUP (ssget))
(COMMAND "PEDIT" "M" group "" "Y" "J" "" "") (princ)
(PRINC)
)

;(defun c:pedD (/)
;(SETQ GROUP (ssget))
;(setq n (sslength group))
;(setq l 0)
;(setq line_group (ssadd))
;(while (< l n)
;   (setq TIP   (cdr (ASSOC 0 (ENTGET (SSNAME GROUP L)))))
;   (princ "\n") (princ tip)
;   (IF (OR (= TIP "LINE" ) (= TIP "LWPOLYLINE"))
;      (SETQ line_group (ssadd (SSNAME GROUP L) line_group))
;   )
;   (SETQ L (+ L 1))
;)
;(COMMAND "PEDIT" "M" line_group "" "Y" "J" "" "") (princ)
;(PRINC)
;)
