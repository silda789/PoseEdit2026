;;;;;;;;;;;;;;;;;;;;;;;;;;;;
(defun c:kesitisareti (/)
(setvar "cmdecho" 0)
(SETQ OL (* 0.01 (OLCEK_OKU)))
(if (= (getvar "ATTREQ") 1) (setvar "ATTREQ" 0))
(setq pt1 (getpoint "\n Yerlestirilecek Nokta.....:"))
(command "-insert" (strcat source_pathlisp"Ayar/Ren.Section") pt1 (* 100 OL) "" 0 )
;(command "_.explode" (entlast))
(if (= (getvar "ATTREQ") 0) (setvar "ATTREQ" 1))
(princ)
)
;;;;;;;;;;;;;;;;;;;;;;;;;;;;
(defun c:dkotuIsareti (/)
(setvar "cmdecho" 0)
(SETQ OL (* 0.01 (OLCEK_OKU)))
(if (= (getvar "ATTREQ") 1) (setvar "ATTREQ" 0))
(setq pt1 (getpoint "\n Yerlestirilecek Nokta.....:"))
(command "-insert" (strcat source_pathlisp"Ayar/Ren.F.Elev") pt1 (* 1 OL) "" 0 )
;(command "_.explode" (entlast))
(if (= (getvar "ATTREQ") 0) (setvar "ATTREQ" 1))
(princ)
)
;;;;;;;;;;;;;;;;;;;;;;;;;;;;
(defun c:baslikyazisi (/)
(SETQ OL (* 0.01 (OLCEK_OKU)))
(setq pt1 (getpoint "\n Yerleştirilecek Nokta.....:"))
(entmake (list (cons 0 "TEXT")
  		  (cons 100 "AcDbEntity")
		  (cons 100 "AcDbText")
		  (cons  7 "ren Gost.common")
		  (cons 10 pt1)
		  (cons 11 pt1)
		  (cons  1 "%%UBASLIK%%U")
		  (cons 40 (* 500 OL))
		  (cons 50 0)  ; rotation
		  (cons 51 0.174533)
          (cons 41 1)
		  (cons 72 4)
		  (cons 73 0)
		  (cons  8 "ren.text")
         )
)
)
;;;;;;;;;;;;;;;;;;;;;;;;;
(defun c:aksbalonu (/)
(SETQ OL (* 0.01 (OLCEK_OKU)))
(setq pt1 (getpoint "\n Yerleştirilecek Nokta.....:"))
(entmake (list (cons 0 "CIRCLE")(cons 10 pt1)(cons 40 (* 625 OL))(cons 8 "ren.axis.circle")))
(entmake (list (cons 0 "TEXT")
  		  (cons 100 "AcDbEntity")
		  (cons 100 "AcDbText")
		  (cons  7 "ren Gost.common")
		  (cons 10 pt1)
		  (cons 11 pt1)
		  (cons  1 "X")
		  (cons 40 (* 500 OL))
		  (cons 50 0)  ; rotation
		  (cons 51 0.174533)
          (cons 41 1)
		  (cons 72 4)
		  (cons 73 0)
		  (cons  8 "ren.axis.text")
         )
)
)
