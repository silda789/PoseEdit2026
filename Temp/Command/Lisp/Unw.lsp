;------------------------------------------------------------------------------;
(defun ayarlari_dosyaya_yaz (/)
(setq dosya (open (strcat client_path"Standard/UNIT.TXT") "w"))
(princ (get_tile  "cizim_birimi"        ) dosya )
(princ "\n" dosya)
(princ (get_tile  "pafta_olcegi"        ) dosya )
(princ "\n" dosya)
(princ (get_tile  "hazir_yazi"        ) dosya )
(princ "\n" dosya)
(close dosya)
)
;-------------------------------------------------------------------------------
(defun hazir_yazi_liste ( / )
(setq liste nil)
(setq dosya_adi (strcat source_pathlisp"Ayar/Projeisimleri.txt"))
(setq dosya (open dosya_adi "r"))
(setq yazi_liste_oku  (read-line dosya))
 (while (/= yazi_liste_oku nil)
   (setq liste (cons yazi_liste_oku liste))
   (setq yazi_liste_oku  (read-line dosya))
 )
    (close dosya)
    (setq hazir_liste (reverse liste))
)
;-------------------------------------------------------------------------------
(defun cizim_birimi_act        ( / )
(ayarlari_dosyaya_yaz)
)
;-------------------------------------------------------------------------------
(defun pafta_olcegi_act        ( / )
(ayarlari_dosyaya_yaz)
)
;-------------------------------------------------------------------------------
(defun tablo_dili_act        ( / )
(ayarlari_dosyaya_yaz)
)
;-------------------------------------------------------------------------------
(defun ayarla_act               ( / )
(ayarlari_dosyaya_yaz)
(done_dialog 4)
)
;-------------------------------------------------------------------------------
(defun hazir_yazi_act        ( / )
(nth (atoi (get_tile "hazir_yazi")) hazir_liste)
(ayarlari_dosyaya_yaz)
)
;-------------------------------------------------------------------------------
(defun ayarlari_dosyadan_oku (/)
(setq dosya (open (strcat client_path"Standard/UNIT.TXT") "r"))
(setq cizim_birimi         (read-line dosya)  )
(setq pafta_olcegi         (read-line dosya)  )
(setq hazir_yazi         (read-line dosya)  )
(close dosya)
)
;-------------------------------------------------------------------------------
(defun yazi_basla (/)
(ayarlari_dosyadan_oku)
(hazir_yazi_liste)
(start_list "hazir_yazi")     (mapcar 'add_list hazir_liste) (end_list)
(set_tile  "cizim_birimi"        cizim_birimi        )
(set_tile  "pafta_olcegi"        pafta_olcegi        )
(set_tile  "hazir_yazi"        hazir_yazi        )

)
;-------------------------------------------------------------------------------
(defun c:Unn ( / )
(setvar "cmdecho" 0)
        (setq id (load_dialog (strcat source_pathlisp"Lisp/Unw.dcl")))
        (if (not (new_dialog "Standart_Ayarlar_dialog" id))(exit))
           (action_tile "cizim_birimi"       "(cizim_birimi_act)" )
           (action_tile "pafta_olcegi"       "(pafta_olcegi_act)"  )
           (action_tile "hazir_yazi"        "(hazir_yazi_act)"        )
           (action_tile "ayarla"               "(ayarla_act)"               )
           (action_tile "ad_cik"               "(done_dialog)  (exit)"      )
           (action_tile "cancel"               "(done_dialog)  (exit)"      )

      (yazi_basla)
    (setq dialog-state (start_dialog))
(setvar "cmdecho" 1)
)
;------------------------------------------------------------------------------;
