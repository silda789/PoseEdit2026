;-------------------------------------------------------------------------------

(defun c:don2 ( / dnt1 dnt2 ara tanim mesafe adet nokta)
(setq clayer_old   (getvar "clayer"  ))
(setq luprec_old   (getvar "luprec"  ))
(setq osmode_old   (getvar "osmode"  ))
(setvar "osmode" 0 )
(setq dnt1 (entget (car (entsel "\n 1.Donatiyi secin..."))))
(setq dnt2 (entget (car (entsel "\n 2.Donatiyi secin..."))))
(setq ara  (getreal             "\n Donati araligi    :"))

(if (= ara nil)
   (progn
         (setq adet (+ 1 (getreal             "\n Ara donati adeti  :")))
         (if (= adet nil ) (exit))
    )
)
(setq tanim (cdr (assoc 0 dnt1)))
(if (= tanim "LWPOLYLINE")
 (progn
  (setq r1 (cdr (assoc 40 dnt1)))
  (setq r2 (cdr (assoc 40 dnt2)))
  (setq n1 (donut_center dnt1))
  (setq n2 (donut_center dnt2))
 )
 (progn
   (setq r1 (cdr (assoc 40 dnt1)))
   (setq n1 (cdr (assoc 10 dnt1)))
   (setq r2 (cdr (assoc 40 dnt2)))
   (setq n2 (cdr (assoc 10 dnt2)))
 )
)
(setq mesafe (distance n1 n2))
(princ mesafe)
(setq aci    (angle n1 n2))
(setq dik    (/ pi 2))
(if (= adet nil)
  (progn
   (setq adet (fix (+ 0.90 (/ mesafe ara))))
   (setq ara  (/ mesafe adet))
  )
)
(if (= ara nil)
  (progn
   (setq ara  (/ mesafe adet))
  )
)
(setq katman (cdr (assoc 8 dnt1)))
(setq nokta (polar n1 aci ara))
(setq l 1)
(setvar "clayer"  katman)
(if (= tanim "LWPOLYLINE")
(progn
(while (< l adet)
  (setq r11 (* r1 2))
  (command "donut" 0 r11 nokta "" )
  (setq nokta (polar nokta aci ara))
  (setq l (+ l 1))
))

(progn
(while (< l adet)
  (command "circle" nokta r1 )
  (setq nokta (polar nokta aci ara))
  (setq l (+ l 1))
)))
(princ "\n Donati adeti: ")(princ (+ adet 1))
(setvar "clayer"   clayer_old   )
(setvar "luprec"   luprec_old   )
(setvar "osmode"   osmode_old   )
(princ)
)

;;;;;;;;;;;;;;;;;;;;;;;;;;;;;;;;;;;;;;;;;;;;

(defun c:don ( / )
              (setq clayer_old   (getvar "clayer"  ))
              (setq luprec_old   (getvar "luprec"  ))
              (setq osmode_old   (getvar "osmode"  ))
              (setvar "osmode" 0 )
              (setq dnt1 (entget (car (entsel "\n 1.Donatiyi secin..."))))
              (setq dnt2 (entget (car (entsel "\n 2.Donatiyi secin..."))))
               (if (= donatiaraligi nil) (progn (initget 1)(setq donatiaraligi (getreal "\nDonati araligi :")))
                      (progn
                      (princ (strcat "\nDonati araligi <" (rtos donatiaraligi 2 1)"> : "))
                      (setq donatiaraligi1  (getreal ))
                      (if (or (= donatiaraligi1 nil)(= donatiaraligi1 ""))
                          (setq donatiaraligi donatiaraligi)
                          (setq donatiaraligi donatiaraligi1)
                      );for if
                      );for progn
               )
               (setq ara donatiaraligi)
              (command "_.undo" "group")
              (setq tanim (cdr (assoc 0 dnt1)))
       (if (= tanim "LWPOLYLINE")
           (progn
                 (setq r1 (cdr (assoc 40 dnt1)))
                 (setq r2 (cdr (assoc 40 dnt2)))
                 (setq n1 (donut_center dnt1))
                 (setq n2 (donut_center dnt2))
           )
           (progn
                 (setq r1 (cdr (assoc 40 dnt1)))
                 (setq n1 (cdr (assoc 10 dnt1)))
                 (setq r2 (cdr (assoc 40 dnt2)))
                 (setq n2 (cdr (assoc 10 dnt2)))
           )
       )
           (setq katman (cdr (assoc 8 dnt1)))
           (setvar "clayer"  katman)
           (setq mesafe (distance n1 n2))
           (setq aci    (angle n1 n2))
           (setq dik    (/ pi 2))
           (setq adet (fix (/ mesafe ara)))
           (setq mes1 (* adet ara))
       (if (= mesafe mes1)
           (progn
                 (setq n3 n1)
           )
           (progn
                 (setq mes2 (- mesafe mes1))
                 (setq mes5 (+ mes2 ara))
                 (setq mes3 (/ mes5 2))
                 (setq n3 (polar n1 (+ aci 0) mes3))
           (if (= tanim "LWPOLYLINE")
           (progn
                 (command "donut" 0 (* r1 2) n3 ""))
           (progn
                 (command "circle" n3 r1 )
           )
       )
           )
       )

           (setq l 1)
       (if (= tanim "LWPOLYLINE")
           (progn
                 (while (< l adet)
                        (setq nokta (polar n3 (+ aci 0) ara))
                        (command "donut" 0 (* r1 2) nokta "" )
                        (setq l (+ l 1))
                        (setq n3 nokta))
                        (princ)
           )
       )
                 (while (< l adet)
                        (setq nokta (polar n3 (+ aci 0) ara))
                        (command "circle" nokta r1 )
                        (setq l (+ l 1))
                        (setq n3 nokta)
                        (princ)
                 )
   (command "_.undo" "e")
   (setvar "clayer"   clayer_old   )
   (setvar "osmode"   osmode_old   )
   (setvar "luprec"   luprec_old   )
)
