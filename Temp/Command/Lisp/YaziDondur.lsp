(defun c:cv (/)
(setq B (ssget '((-4 . "<OR") (0 . "TEXT") (0 . "MTEXT") (0 . "INSERT") (0 . "ATTDEF") (-4 . "OR>") )))
(setq N (sslength B))
(setq L 0)
(setq yeni_aci (getreal " Yeni açý : "))
       (if (= yeni_aci nil)
          (progn
              (setq eleman (car (entsel "\n Aci alinacak line belirtin... "     )))
                  (IF (= "LINE" (cdr (assoc 0 (entget eleman))))
                         (setq yeni_aci (angle  (cdr (assoc 10 (entget eleman))) (cdr (assoc 11 (entget eleman))))))
                  (IF (= "ARC" (cdr (assoc 0 (entget eleman))))
                      (progn
                         (setq merkez        (cdr (assoc 10 (ENTGET eleman))))
                         (setq yaricap       (cdr (assoc 40 (ENTGET eleman))))
                         (setq baslangic_aci (cdr (assoc 50 (ENTGET eleman))))
                         (setq bitis_aci     (cdr (assoc 51 (ENTGET eleman))))
                         (setq BASKOR (POLAR merkez baslangic_aci yaricap))
                         (setq SONKOR (POLAR merkez bitis_aci     yaricap))
                         (setq yeni_aci (angle  BASKOR SONKOR))
                      )
                  )
             (setq yeni_aci (/ (* yeni_aci 180) PI))
          )
       )
(if (and (> yeni_aci 90) (< yeni_aci 270)) (setq yeni_aci (- yeni_aci 180)))
(while (< L N)
(setq PT1        (cdr (ASSOC 10 (ENTGET (SSNAME B L)))))
(setq MEVCUT_ACI (cdr (ASSOC 50 (ENTGET (SSNAME B L)))))
(setq MEVCUT_ACI (/ (* MEVCUT_ACI 180) PI))
(SETQ DONDUR_ACI (- yeni_aci MEVCUT_ACI ))
(setq osmode_old   (getvar "osmode"  ))
(setvar "osmode"   0)
(command "_rotate" (SSNAME B L) "" PT1 DONDUR_ACI)
(setvar "osmode"   osmode_old   )
(setq L (+ L 1))
)
)
