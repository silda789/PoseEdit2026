(defun c:kk (/)
(setq OL (* 0.01 (OLCEK_OKU)))
(setq pt2 (GETPOINT "\n Ilk Noktayi Seciniz:"))
(setq pt3 (GETPOINT pt2 "\n Ikinci Noktayi Seciniz:"))
(layer_yap "ren.secondary"  "8" "HIDDEN2")
      (if (= pt3 nil)
         (progn
(SETQ pt3 (GETPOINT pt2 "\n Ikinci Noktayi Seciniz:"))
(entmake (list '(0 . "LWPOLYLINE") '( 100 . "AcDbEntity") '(67 . 0)
                 '( 100 . "AcDbPolyline") '(90 . 6) '(70 . 0) '(43 . 0.0)
                 '(38 . 0.0) '(39 . 0.0) (cons 8 "ren.secondary") (cons 48 ( * ol 1000)) (cons 10 pt2) (cons 10 pt3)))
(setq pt1 (getpoint "\n Yerlestirilecek Nokta.....:"))
(setq aci   (angle pt2 pt3))
(entdel (entlast))

)
         (progn
(setq aci   (angle pt2 pt3))
(SETQ pt1 (POLAR pt2 (+ aci 0) (/ (distance pt2 pt3) 2) ))

)
)
(SETQ nk7 (POLAR pt2  (+ aci PI) (* ol 150 )))
(SETQ nk8 (POLAR pt3  (+ aci 0) (* ol 150 )))
(SETQ NK1 (POLAR pt1 (+ aci (* PI 1.5 )) (* ol 150 )))
(SETQ NK2 (POLAR nk1 (+ aci PI)  (* ol 40 )))
(SETQ NK3 (POLAR pt1 (+ aci (* PI 0.5 )) (* ol 150 )))
(SETQ NK4 (POLAR nk3 (+ aci 0) (* ol 40 )))
(SETQ NK5 (POLAR pt1 (+ aci pi) (* ol 60 )))
(SETQ NK6 (POLAR pt1 (+ aci 0) (* ol 60 )))
(entmake (list '(0 . "LWPOLYLINE") '( 100 . "AcDbEntity") '(67 . 0)
                 '( 100 . "AcDbPolyline") '(90 . 6) '(70 . 0) '(43 . 0.0)
                 '(38 . 0.0) '(39 . 0.0) (cons 8 "ren.secondary") (cons 48 ( * ol 1000)) (cons 10 nk7) (cons 10 nk5)
                 (cons 10 nk2) (cons 10 nk4) (cons 10 nk6) (cons 10 nk8)))
(princ)
)

(defun kesikciz ( pt2 pt3 / )
(setq OL (* 0.01 (OLCEK_OKU)))
(layer_yap "ren.secondary"  "8" "HIDDEN2")
(setq aci   (angle pt2 pt3))
(SETQ pt1 (POLAR pt2 (+ aci 0) (/ (distance pt2 pt3) 2) ))
(SETQ nk7 (POLAR pt2  (+ aci PI) (* ol 150 )))
(SETQ nk8 (POLAR pt3  (+ aci 0) (* ol 150 )))
(SETQ NK1 (POLAR pt1 (+ aci (* PI 1.5 )) (* ol 150 )))
(SETQ NK2 (POLAR nk1 (+ aci PI)  (* ol 40 )))
(SETQ NK3 (POLAR pt1 (+ aci (* PI 0.5 )) (* ol 150 )))
(SETQ NK4 (POLAR nk3 (+ aci 0) (* ol 40 )))
(SETQ NK5 (POLAR pt1 (+ aci pi) (* ol 60 )))
(SETQ NK6 (POLAR pt1 (+ aci 0) (* ol 60 )))
(entmake (list '(0 . "LWPOLYLINE") '( 100 . "AcDbEntity") '(67 . 0)
                 '( 100 . "AcDbPolyline") '(90 . 6) '(70 . 0) '(43 . 0.0)
                 '(38 . 0.0) '(39 . 0.0) (cons 8 "ren.secondary") (cons 48 ( * ol 1000)) (cons 10 nk7) (cons 10 nk5)
                 (cons 10 nk2) (cons 10 nk4) (cons 10 nk6) (cons 10 nk8)))
(princ)
)
;;;;;;;;;;;;;;;
;(defun c:kk1(/ t1 t2 t3 t4)
;(setq osmode_old   (getvar "osmode"  ))
;(setq clayer_old   (getvar "clayer"  ))
;(layer_yap "ren.kesikcizgi.ince"  "8" "HIDDEN2")
;(command "clayer" "ren.kesikcizgi.ince")
;(setq t1 (getpoint "\nIlk noktayi seciniz: "))
;(setq t2 (getpoint t1 "\nCapraz noktasini seciniz: "))
;(setq t3 (getpoint t2 "\nCapraz noktasini seciniz: "))
;(setq aci (angle t2 t3))
;(setq t4 (polar t1 aci (distance t2 t3)))
;(kesikciz t1 t2)
;(kesikciz t4 t3)
;(command "pline" x1 x3 x2 x1 x4 x2 x3 x4 "" )
;(command "wipeoutframe" "0" )
;(command "wipeout" t1 t2 t3 t4 "" )
;(kesikciz t1 t2)
;(kesikciz t4 t3)
;(setvar "clayer"   clayer_old   )
;(setvar "osmode"   osmode_old   )
;(princ)
;)
;;;;;;;;;;;;;;;
(defun c:ot(/ x1 x2 x3 x4 dx dy t1 t2)
(setq osmode_old   (getvar "osmode"  ))
(setq clayer_old   (getvar "clayer"  ))
(layer_yap "ren.secondary"  "8" "HIDDEN2")
(command "clayer" "ren.secondary")
(setq t1 (getpoint "\nIlk noktayi seciniz: "))
(setq t2 (getpoint t1 "\nCapraz noktasini seciniz: "))
(setq dx (- (car t2) (car t1)))
(setq dy (- (cadr t2) (cadr t1)))
(if (< dx 0) (progn
(setq x2 t1)
(setq x1 (polar x2 0 dx))
);progn
  (progn
(setq x1 t1)
(setq x2 (polar x1 0 dx))
));progn,if
(setq x3 (polar x2 (/ pi 2) dy))
(setq x4 (polar x1 (/ pi 2) dy))

(setq x1 (trans x1 1 0))
(setq x2 (trans x2 1 0))
(setq x3 (trans x3 1 0))
(setq x4 (trans x4 1 0))
(command "pline" x1 x3 x2 x1 x4 x2 x3 x4 "" )
(setvar "clayer"   clayer_old   )
(setvar "osmode"   osmode_old   )
(princ)
);defun ot
