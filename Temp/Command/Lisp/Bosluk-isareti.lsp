(vl-load-com)
(setq acad_application (vlax-get-acad-object))
(setq active_document (vla-get-ActiveDocument acad_application))
(setq model_space (vla-get-ModelSpace active_document))

;;;;;;;;;;;;;;;;;;;;
(defun c:ett (  /  )
       (SETQ OL (* 0.01 (OLCEK_OKU)))
       (setq clayer_old   (getvar "clayer"  ))
       (setq osmode_old   (getvar "osmode"  ))
       (setvar "osmode"   0)
       (command "clayer" "ren.arrow")
       (setq dnt1 (entget (car (entsel "\n 1.Donatiyi secin..."))))
       (setq dnt2 (entget (car (entsel "\n 2.Donatiyi secin..."))))
       (if (= donatiarasimesafe nil) (progn (initget 1)(setq donatiarasimesafe (getreal "\nMesafeyi Girin :")))
                      (progn
                            (princ (strcat "\nMesafeyi Girin <" (rtos donatiarasimesafe 2 1)"> : "))
                            (setq donatiarasimesafe1  (getreal ))
                            (if (or (= donatiarasimesafe1 nil)(= donatiarasimesafe1 ""))
                                (setq donatiarasimesafe donatiarasimesafe)
                                (setq donatiarasimesafe donatiarasimesafe1)
                            )
                      )
       )
       (setq mes donatiarasimesafe)
       (command "_.undo" "group")
       (setq tanim (cdr (assoc 0 dnt1)))
             (if (= tanim "LWPOLYLINE")
                 (progn
                       (setq yc1 (cdr (assoc 40 dnt1)))
                       (setq yc2 (cdr (assoc 40 dnt2)))
                       (setq nk1 (donut_center dnt1))
                       (setq nk4 (donut_center dnt2))
                )
                 (progn
                       (setq nk1 (cdr (assoc 10 dnt1)))
                       (setq nk4 (cdr (assoc 10 dnt2)))
                 )
             )
             (setq obje (ssget "_F" (list nk1 nk4) (list '(-4 . "<OR") '(-4 . "<AND")
              '(0 . "LWPOLYLINE") '(90 . 2) '(70 . 1) '(-4 . "AND>")
              '(0 . "CircLe") '(-4 . "OR>"))))
       (setq L 0)
       (setq aci   (angle nk1 nk4))
       (setq nk2 (polar nk1 (+ aci (* pi 0.5)) mes))
       (setq nk3 (polar nk4 (+ aci (* pi 0.5)) mes))
       (command "line" nk2 nk3 "")
       (setq N (SSLENGTH obje))
       (while (< l n)
              (if (= tanim "LWPOLYLINE")
                  (progn
                        (setq eleman (ENTGET (SSNAME obje L)))
                        (setq yc3 (cdr (assoc 40 eleman)))
                        (setq nk5 (donut_center eleman))
                  )
                  (progn
                        (setq eleman (ENTGET (SSNAME obje L)))
                        (setq nk5 (cdr (assoc 10 eleman)))
                  )
              )
              (setq nk6 (polar nk5 (+ aci (/ pi 2 )) mes))
              (command "line" nk5 nk6 "")
              (setq l (+ l  1))
       (princ)
       )
       (command "_.undo" "e")
       (setvar "clayer"   clayer_old   )
       (setvar "osmode"   osmode_old   )
       (princ)
)
;;;;;;;;;;;;;;;
(defun c:ot(/ x1 x2 x3 x4 dx dy t1 t2)
(setq osmode_old   (getvar "osmode"  ))
(setq clayer_old   (getvar "clayer"  ))
(command "clayer" "ren.secondary")
(setq t1 (getpoint "\nIlk noktayi seciniz: "))
(setq t2 (getpoint t1 "\nCapraz noktasini seciniz: "))
(setq dx (- (car t2) (car t1)))
(setq dy (- (cadr t2) (cadr t1)))
(if (< dx 0) (progn
(setq x2 t1)
(setq x1 (polar x2 0 dx))
);progn
  (progn
(setq x1 t1)
(setq x2 (polar x1 0 dx))
));progn,if
(setq x3 (polar x2 (/ pi 2) dy))
(setq x4 (polar x1 (/ pi 2) dy))

(setq x1 (trans x1 1 0))
(setq x2 (trans x2 1 0))
(setq x3 (trans x3 1 0))
(setq x4 (trans x4 1 0))
(command "pline" x1 x3 x2 x1 x4 x2 x3 x4 "" )
(setvar "clayer"   clayer_old   )
(setvar "osmode"   osmode_old   )
(princ)
);defun ot
