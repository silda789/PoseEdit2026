;-------------------------------------------------------------------------------
;                                                                              ;
;                                                                              ;
;                            Bul değiştir.....                                 ;
;                                                                              ;
;                                                                              ;
;-------------------------------------------------------------------------------
(defun ct_act ( os ns p / )
(setq i 0)
(setq degis 0)
(repeat (sslength p )
     (setq ent (entget (ssname p i)))
     (setq kontrol_yazisi (cdr (assoc 1 (entget (ssname p i)))))
     (if (/= (vl-string-search os kontrol_yazisi ) nil)
        (progn
          (setq position (vl-string-search os kontrol_yazisi))
          (while (/= (setq position (vl-string-search os kontrol_yazisi position)) nil)
          (setq kontrol_yazisi  (vl-string-subst ns os kontrol_yazisi position))
          (setq position (min (+ position (strlen ns)) (strlen kontrol_yazisi)))
          )
          (setq ent (subst (cons 1 kontrol_yazisi) (assoc 1 ent) ent))
          (entmod ent)
          (entupd (ssname p i))
          (setq degis (1+ degis))
        )
     )
  (setq i (1+ i))
)
)

(defun c:ct ( / )
(vl-load-com)
(setvar "cmdecho" 1)
(princ "Yazı seçiniz.............") (setq p (ssget '((0 . "TEXT"))))
(setq os (getstring "\n Eski Yazi : " t))(if (= os "")(progn (setq os_ (ssget ":S" '((0 . "TEXT"))))(if (= os_ nil)(setq os "")(setq os (cdr (assoc 1 (entget (ssname os_ 0))))))))
(setq ns (getstring "\n Yeni Yazi : " t))(if (= ns "")(progn (setq ns_ (ssget ":S" '((0 . "TEXT"))))(if (= ns_ nil)(setq ns "")(setq ns (cdr (assoc 1 (entget (ssname ns_ 0))))))))
(ct_act os ns p)
(princ (strcat "\n Değişen eleman sayısı : " (itoa degis)))
(setvar "cmdecho" 0)
(princ)
)
;-------------------------------------------------------------------------------
(defun c:yu ( / )
(vl-load-com)
(setvar "cmdecho" 1)
(setq ns_ (ssget ":S" '((0 . "TEXT"))))(if (= ns_ nil)(setq ns "")(setq ns (cdr (assoc 1 (entget (ssname ns_ 0))))))
(princ "Yazı seçiniz.............") (setq p (ssget '((0 . "TEXT"))))
(setq i 0)
(repeat (sslength p )
     (setq ent (entget (ssname p i)))
     (setq kontrol_yazisi (cdr (assoc 1 (entget (ssname p i)))))
     (setq kontrol_yazisi  (vl-string-subst ns kontrol_yazisi kontrol_yazisi))
     (setq ent (subst (cons 1 kontrol_yazisi) (assoc 1 ent) ent))
     (entmod ent)
     (setq i (1+ i))
)
(setvar "cmdecho" 0)
(princ)
)
;;;;;;;;;;;;;;;;;;;
;Block yazilarini birbirine kopyalar
(defun att_yaz (en tag value)
(vl-load-com)
(setq block  (vlax-ename->vla-object en))
(setq tag (strcase tag))
(foreach attrib (vlax-invoke block 'GetAttributes) (if (eq tag (strcase (vla-get-TagString attrib))) (progn (vla-put-TextString attrib value) value)))
)

(defun c:kx (/)
(vl-load-com)
(setq en1 (car (entsel "\n Okunacak Poz' u seç... "        )))
(setq blk  (vlax-ename->vla-object en1))
(setq atts (vlax-invoke blk 'getattributes))
(princ "\n Degistirilecek Pozlari seç... " )
(setq B (ssget (list (cons 0 "INSERT"))))
(while (/= b nil)
 (setq i 0)
 (setq en2 (ssname B i))
  (while (< i (sslength b))
      (foreach att atts
       (setq pn (vlax-get-property att 'TagString))
       (setq pv (vlax-get-property att 'TextString))
       (att_yaz en2 pn pv)
      )
   (setq i (1+ i))
   (setq en2 (ssname B i))
  )
 (princ "\n Degistirilecek Pozlari seç... " )
 (setq B (ssget (list (cons 0 "INSERT"))))
)
(princ)
)
