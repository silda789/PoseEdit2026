(vl-load-com)
(setq acad_application (vlax-get-acad-object))
(setq active_document (vla-get-ActiveDocument acad_application))
(setq model_space (vla-get-ModelSpace active_document))

;;;;;;;;;;;;;;;;;;;;
(defun c:ett (  /  )
       (SETQ OL (* 0.01 (OLCEK_OKU)))
       (setq clayer_old   (getvar "clayer"  ))
       (setq osmode_old   (getvar "osmode"  ))
       (setvar "osmode"   0)
       (command "clayer" "ren.arrow")
       (setq dnt1 (entget (car (entsel "\n 1.Donatiyi secin..."))))
       (setq dnt2 (entget (car (entsel "\n 2.Donatiyi secin..."))))
       (if (= donatiarasimesafe nil) (progn (initget 1)(setq donatiarasimesafe (getreal "\nMesafeyi Girin :")))
                      (progn
                            (princ (strcat "\nMesafeyi Girin <" (rtos donatiarasimesafe 2 1)"> : "))
                            (setq donatiarasimesafe1  (getreal ))
                            (if (or (= donatiarasimesafe1 nil)(= donatiarasimesafe1 ""))
                                (setq donatiarasimesafe donatiarasimesafe)
                                (setq donatiarasimesafe donatiarasimesafe1)
                            )
                      )
       )
       (setq mes donatiarasimesafe)
       (command "_.undo" "group")
       (setq tanim (cdr (assoc 0 dnt1)))
             (if (= tanim "LWPOLYLINE")
                 (progn
                       (setq yc1 (cdr (assoc 40 dnt1)))
                       (setq yc2 (cdr (assoc 40 dnt2)))
                       (setq nk1 (donut_center dnt1))
                       (setq nk4 (donut_center dnt2))
                )
                 (progn
                       (setq nk1 (cdr (assoc 10 dnt1)))
                       (setq nk4 (cdr (assoc 10 dnt2)))
                 )
             )
             (setq obje (ssget "_F" (list nk1 nk4) (list '(-4 . "<OR") '(-4 . "<AND")
              '(0 . "LWPOLYLINE") '(90 . 2) '(70 . 1) '(-4 . "AND>")
              '(0 . "CircLe") '(-4 . "OR>"))))
       (setq L 0)
       (setq aci   (angle nk1 nk4))
       (setq nk2 (polar nk1 (+ aci (* pi 0.5)) mes))
       (setq nk3 (polar nk4 (+ aci (* pi 0.5)) mes))
       (command "line" nk2 nk3 "")
       (setq N (SSLENGTH obje))
       (while (< l n)
              (if (= tanim "LWPOLYLINE")
                  (progn
                        (setq eleman (ENTGET (SSNAME obje L)))
                        (setq yc3 (cdr (assoc 40 eleman)))
                        (setq nk5 (donut_center eleman))
                  )
                  (progn
                        (setq eleman (ENTGET (SSNAME obje L)))
                        (setq nk5 (cdr (assoc 10 eleman)))
                  )
              )
              (setq nk6 (polar nk5 (+ aci (/ pi 2 )) mes))
              (command "line" nk5 nk6 "")
              (setq l (+ l  1))
       (princ)
       )
       (command "_.undo" "e")
       (setvar "clayer"   clayer_old   )
       (setvar "osmode"   osmode_old   )
       (princ)
)
;;;;;;;;;;;;;;;
(defun c:ot(/ x1 x2 x3 x4 dx dy t1 t2)
(setq osmode_old   (getvar "osmode"  ))
(setq clayer_old   (getvar "clayer"  ))
(command "clayer" "ren.secondary")
(setq t1 (getpoint "\nIlk noktayi seciniz: "))
(setq t2 (getpoint t1 "\nCapraz noktasini seciniz: "))
(setq dx (- (car t2) (car t1)))
(setq dy (- (cadr t2) (cadr t1)))
(if (< dx 0) (progn
(setq x2 t1)
(setq x1 (polar x2 0 dx))
);progn
  (progn
(setq x1 t1)
(setq x2 (polar x1 0 dx))
));progn,if
(setq x3 (polar x2 (/ pi 2) dy))
(setq x4 (polar x1 (/ pi 2) dy))

(setq x1 (trans x1 1 0))
(setq x2 (trans x2 1 0))
(setq x3 (trans x3 1 0))
(setq x4 (trans x4 1 0))
(command "pline" x1 x3 x2 x1 x4 x2 x3 x4 "" )
(setvar "clayer"   clayer_old   )
(setvar "osmode"   osmode_old   )
(princ)
);defun ot



(defun c:tet (  /  )
       (vl-load-com)
       (terpri)
       (setq ciz (ssget '((0 . "line"))))
       (setq L 0)
       (setq N (SSLENGTH ciz))
       (while (< l n)
       (setq eleman (ENTGET (SSNAME ciz L)))

       (setq nk1 (cdr (assoc 10 eleman)))
       (setq nk2 (cdr (assoc 11 eleman)))
       (setq aci (angle nk1 nk2))
       (setq y1 (polar nk1 (+ aci (* -0.5 pi)) (GETVAR "DIMDLE")))
       (setq y2 (polar nk2 (+ aci (* -0.5 pi)) (GETVAR "DIMDLE")))
       (entdel (SSNAME ciz L) )
       (setq obj (vla-AddDimRotated model_space (vlax-3D-point y1) (vlax-3D-point y2)
                 (vlax-3D-point (polar y2 (+ aci (* pi 0.5)) (GETVAR "DIMDLE"))) aci))
	(vla-put-Layer obj "ren.arrow")
    (princ)
    (setq l (+ l  1)))
)

;;;;;;;;;;;;;;;;;;;;;;;;;;;;;
(defun c:tet1 (  /  )
       (vl-load-com)
       (terpri)
       (setq ciz (ssget '((0 . "arc"))))
       (setq L 0)
       (setq N (SSLENGTH ciz))
       (while (< l n)
       (setq eleman (ENTGET (SSNAME ciz L)))

       (setq nk1 (cdr (assoc 10 eleman)))
       (setq nk2 (cdr (assoc 11 eleman)))
       (setq aci (angle nk1 nk2))
       (setq y1 (polar nk1 (+ aci (* -0.5 pi)) (GETVAR "DIMDLE")))
       (setq y2 (polar nk2 (+ aci (* -0.5 pi)) (GETVAR "DIMDLE")))
       (entdel (SSNAME ciz L) )
       (setq obj (vla-AddDimRotated model_space (vlax-3D-point y1) (vlax-3D-point y2)
                 (vlax-3D-point (polar y2 (+ aci (* pi 0.5)) (GETVAR "DIMDLE"))) aci))
	(vla-put-Layer obj "ren.arrow")
    (princ)
    (setq l (+ l  1)))
)





(defun c:tet2 (  / obj )
       (vl-load-com)
       (SETQ OL (GETVAR "DIMSCALE"))
       (SETQ OL1 (GETVAR "DIMLFAC"))
       (terpri)
       (setq shv (* ol 25))
(setq en (car (entsel "\n Arc Seciniz " )))
(setq blk  (vlax-ename->vla-object en))
(setq atts (vlax-invoke blk 'getattributes))
(foreach att atts
(setq pn   (vlax-get-property att 'TagString))
(if (= pn "PNO")
(progn
(setq nk1  (vlax-get-property att 'EndPoint    ))
(setq nk2  (vlax-get-property att 'StartPoint      ))
(setq nk3  (vlax-get-property att 'Center      ))

)))

       (setq obj (vla-add-dimarc model_space (vla-get-center nk3) (vlax-3D-point nk1) (vlax-3D-point nk2) (vlax-3d-point a4)
         ))

    (vla-put-StyleName obj "ren ar 100")


)

(defun c:autoaldim ( / osm g pt1 pt2 sss k ent plpts m n cen dst txt txta ss ptab ce ptabn enta ) (vl-load-com)
(prompt "\nSelect polylines or lines objects for automatic aligned dimensioning")
(setq osm (getvar 'osmode))
(setvar 'osmode 0)
(setq sss (ssget '((0 . "LWPOLYLINE,LINE"))))
(setq k (sslength sss))
(setq cen (getvar 'viewctr))
(setq txt (entmakex (list '(0 . "TEXT") '(100 . "AcDbEntity") '(100 . "AcDbText") '(1 . "0.0") (cons 10 cen) (cons 40 (/ (getvar 'viewsize) 50)) )))
(setq txta (vlax-ename->vla-object txt))
(setq ss (ssget "_L"))
(prompt "\nPress any key to enter offset distance manually")
(while (= (sslength ss) 1)
(setq g (grread T))
(if (= (car g) 3) (progn (vla-erase txta) (ssdel txt ss)))
(if (= (car g) 2) (progn (setq dst (getdist "\nInput offset distance for aligned dimensions <2 points or number> : ")) (vla-erase txta) (ssdel txt ss)))
(if (= (car g) 5) (progn (setq dst (distance cen (cadr g))) (vla-put-textstring txta dst)))
)
(while (>= k 1)
(setq ent (ssname sss (setq k (1- k))))
(if (eq (cdr (assoc 0 (entget ent))) "LINE")
(command "_.dimaligned" (setq pt1 (cdr (assoc 10 (entget ent)))) (setq pt2 (cdr (assoc 11 (entget ent)))) (nor*dst pt1 pt2 dst) )
)
(if (eq (cdr (assoc 0 (entget ent))) "LWPOLYLINE")
(progn
(setq enta (vlax-ename->vla-object ent))
(setq plpts (mapcar '(lambda (x) (cdr x)) (vl-remove-if-not '(lambda (x) (= (car x) 10)) (entget ent)) ))
(setq m -1)
(repeat (- (length plpts) 1)
(setq m (1+ m))
(setq n (1+ m))
(if (and (/= (ssget "_C" (mid (nth m plpts) (nth n plpts)) (mid (nth m plpts) (nth n plpts))) nil) (eq ent (ssname (ssget "_C" (mid (nth m plpts) (nth n plpts)) (mid (nth m plpts) (nth n plpts))) 0)))
(command "_.dimaligned" (setq pt1 (nth m plpts)) (setq pt2 (nth n plpts)) (nor*dst pt1 pt2 dst) )
(progn
(setq ptab (vlax-curve-getpointatparam enta (+ (vlax-curve-getparamatpoint enta (nth m plpts)) (/ (- (vlax-curve-getparamatpoint enta (nth n plpts)) (vlax-curve-getparamatpoint enta (nth m plpts))) 2))))
(setq ce (cent (if (= (length (nth m plpts)) 2) (append (nth m plpts) (list 0.0)) (nth m plpts)) (if (= (length ptab) 2) (append ptab (list 0.0)) ptab) (if (= (length (nth n plpts)) 2) (append (nth n plpts) (list 0.0)) (nth n plpts))))
(setq ptabn (polar ptab (angle ce ptab) dst))
(command "_.dimarc" ptab ptabn)
)
)
)
(if (and (eq n (- (length plpts) 1)) (eq (cdr (assoc 70 (entget ent))) 1))
(if (and (/= (ssget "_C" (mid (nth n plpts) (nth 0 plpts)) (mid (nth n plpts) (nth 0 plpts))) nil) (eq ent (ssname (ssget "_C" (mid (nth n plpts) (nth 0 plpts)) (mid (nth n plpts) (nth 0 plpts))) 0)))
(command "_.dimaligned" (setq pt1 (nth n plpts)) (setq pt2 (nth 0 plpts)) (nor*dst pt1 pt2 dst) )
(progn
(setq ptab (vlax-curve-getpointatparam enta (+ (vlax-curve-getparamatpoint enta (nth n plpts)) (/ (- (vlax-curve-getendparam enta) (vlax-curve-getparamatpoint enta (nth n plpts))) 2))))
(setq ce (cent (if (= (length (nth n plpts)) 2) (append (nth n plpts) (list 0.0)) (nth n plpts)) (if (= (length ptab) 2) (append ptab (list 0.0)) ptab) (if (= (length (nth 0 plpts)) 2) (append (nth 0 plpts) (list 0.0)) (nth 0 plpts))))
(setq ptabn (polar ptab (angle ce ptab) dst))
(command "_.dimarc" ptab ptabn)
)
)
)
)
)
)
(setvar 'osmode osm)
(princ)
)
