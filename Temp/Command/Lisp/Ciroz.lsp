; ---------------------------------------------------------------------
; --- CIROZ CIZER -----------------------------------------------------
; ---------------------------------------------------------------------
; ---------------------------------------------------------------------
(defun cr_ciz ( dnt1 dnt2 / dnt1 dnt2 aci r1 r2 n1 n2 n3 n4 n5 n6 n7 n8 n9 n10 n11 n12 )
(setq blipmode_old (getvar "blipmode"))
(setq cmdecho_old  (getvar "cmdecho" ))
(setq clayer_old   (getvar "clayer"  ))
(setq luprec_old   (getvar "luprec"  ))
(setq osmode_old   (getvar "osmode"  ))
(setvar "osmode" 0 )
(layer_yap "ren.reinforcement"  "7" "continuous")
(command "clayer" "ren.reinforcement")

              (setq tanim (cdr (assoc 0 dnt1)))
       (if (= tanim "LWPOLYLINE")
           (progn
                 (setq r1 (cdr (assoc 40 dnt1)))
                 (setq r2 (cdr (assoc 40 dnt2)))
                 (setq n1 (donut_center dnt1))
                 (setq n2 (donut_center dnt2))

           )
           (progn
                 (setq r1 (cdr (assoc 40 dnt1)))
                 (setq n1 (cdr (assoc 10 dnt1)))
                 (setq r2 (cdr (assoc 40 dnt2)))
                 (setq n2 (cdr (assoc 10 dnt2)))
           )
       )
(setq aci   (angle n1 n2))
(setq r (max r1 r2))
(setq fark  (* r 0.15) )
(setq kanca (* r1 3))
(setq n3 (polar n1 (+ aci  (* pi 0.50))    (+ r fark )))
(setq n4 (polar n1 (+ aci  (* pi 1.25))    (+ r fark )))
(setq n5 (polar n4 (+ aci  (* pi 1.75))          kanca))
(setq n6 (polar n2 (+ aci  (* pi 0.50))  (+ r fark )))
(setq n7 (polar n2 (+ aci  (* pi 0))  (+ r fark )))
(setq n8 (polar n7 (+ aci  (* pi 1.5))          kanca))
(command "pline"  n5 n4 "a" n3 "l" n6 "a" n7 "l" n8 "")
(setvar "blipmode" blipmode_old )
(setvar "cmdecho"  cmdecho_old  )
(setvar "clayer"   clayer_old   )
(setvar "luprec"   luprec_old   )
(setvar "osmode"   osmode_old   )
(princ)
)
(defun c:cr ( / )
(setq dnt1 (entget (car (entsel "\n 1.Donatiyi secin..."))))
(setq dnt2 (entget (car (entsel "\n 2.Donatiyi secin..."))))
(cr_ciz dnt1 dnt2)
)
