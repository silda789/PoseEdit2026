(defun c:rz (/ layerisim layerrengi revtext )
(setq OL (* 0.01 (OLCEK_OKU)))
(setq osmode_old   (getvar "osmode"  ))
(setq clayer_old   (getvar "clayer"  ))
(setq revnumarasi (getreal "\nKacinci Revizyon: "))
(setq layerisim (strcat "ren.rev-"(rtos revnumarasi 2 0 )  ))
(setq layerrengi 30 )
(setq revtext (strcat (rtos revnumarasi 2 0 )".-"  ))
(layer_yap layerisim  layerrengi "continuous")
(command "clayer" layerisim)
(setq pt1 (getpoint "\n Yerlestirilecek Nokta.....:"))
(setvar "osmode"   0)
(setq pt2 (polar pt1 (* 1.35 pi) (* ol 1890)))
(setq pt3 (polar pt2 pi (* ol 1545)))
(setq pt4 (polar pt3 (* 0.35 pi) (* ol 945)))
(setq pt5 (polar pt4 0 (* ol 1545)))
(command "pline" pt1 pt2 pt3 pt4 pt5 "")
(setq pttext (polar pt2 (angle pt2 pt4) (/ (distance pt2 pt4) 2)))
(entmake (list (cons 0 "TEXT")
		  (cons 100 "AcDbEntity")
		  (cons 100 "AcDbText")
		  (cons   7 "ren Gost.common")
		  (cons  10 pttext)
		  (cons  11 pttext)
		  (cons   1 revtext)
		  (cons  40 (* ol 500))
		  (cons  50 0)  ; rotation
		  (cons  41 0.60)
 		  (cons  51 0.174533)
          (cons  72 1)
		  (cons  73 2)
		  (cons   8 layerisim )
         )
)
(setvar "osmode"   osmode_old   )
(setvar "clayer"   clayer_old   )
)
