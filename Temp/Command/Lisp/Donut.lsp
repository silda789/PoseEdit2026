;;;;;;;;;;;;
(defun c:dd (/)
	(setvar "cmdecho" 0)
    (SETQ OL (* 0.01 (OLCEK_OKU)))
	(while (= 0)
           (setq nok1 (getpoint "\n Donatı yeleştirilecek nokta."))
	       (setq nk1 (polar nok1 pi (* ol 37.125)))
	       (setq p3 (list (car nk1) (cadr nk1)))
	       (setq nk2 (polar nok1 0 (* ol 37.125)))
	       (setq p4 (list (car nk2) (cadr nk2)))
	       (entmake (list
					     (cons 0 "LWPOLYLINE")
					     (cons 100 "AcDbEntity")
					     (cons 410 "Model")
					     (cons 8 "ren.arrow")
					     (cons 100 "AcDbPolyline")
					     (cons 90 2)
					     (cons 70 1)
					     (cons 43 (* ol 74.2500))
					     (cons 10 p3)
					     (cons 40 0)
					     (cons 41 0)
					     (cons 42 1.0)
					     (cons 10 p4)
					     (cons 40 0)
					     (cons 41 0)
					     (cons 42 1.0)
				    )
	       )
    )
	(princ)
)
;;;;;;;;;;;;
(defun c:don3 ( / )
(setq osmode_old   (getvar "osmode"  ))
(setq clayer_old   (getvar "clayer"  ))
(setvar "osmode"   0)
(command "clayer" "ren.reinforcement")
(setq dnt1 (ssget '((0 . "circle"))))
(command "_.undo" "group")
(if (= dnt1 nil)
      (progn
        (setq dnt1 (ssget))))
(setq L 0)
(setq N (SSLENGTH dnt1))
(while (< l n)
(setq eleman (ENTGET (SSNAME dnt1 L)))
(setq r1 (cdr (assoc 40 eleman)))
(setq n1 (cdr (assoc 10 eleman)))
(setq r2 (* 2 r1))
(command "donut" 0 r2 n1 "" )
(entdel (SSNAME dnt1 L) )
(princ)(setq l (+ l  1)))
(setvar "osmode"   osmode_old   )
(setvar "clayer"   clayer_old   )
(princ)
(command "_.undo" "e")
)
;;;;;;;;;;;;
(defun c:don4 ( / )
(setq osmode_old   (getvar "osmode"  ))
(setq clayer_old   (getvar "clayer"  ))
(setvar "osmode"   0)
(layer_yap "ren.reinforcement"  "7" "continuous")
(command "clayer" "ren.reinforcement")
(setq dnt1 (ssget '((0 . "LWPOLYLINE"))))
(command "_.undo" "group")
(if (= dnt1 nil)
      (progn
        (setq dnt1 (ssget))))
(setq L 0)
(setq N (SSLENGTH dnt1))
(while (< l n)
(setq eleman (ENTGET (SSNAME dnt1 L)))
(setq r1 (cdr (assoc 40 eleman)))
(setq n1 (donut_center eleman))
(setq r2 (/ 2 r1))
(entmake (list (cons 0 "CIRCLE")
                  (cons 10 n1)
                  (cons 40 r1)
                  (cons 8 "ren.reinforcement")
                  ))
(entdel (SSNAME dnt1 L) )
(princ)(setq l (+ l  1)))
(setvar "osmode"   osmode_old   )
(setvar "clayer"   clayer_old   )
(princ)
(command "_.undo" "e")
)
;;;;;;;;;;;;
