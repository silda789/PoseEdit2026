(defun c:borukapa (/)
(setq osmode_old   (getvar "osmode"  ))
(setvar "osmode"   0)
(setq B (SSGET '((0 . "CIRCLE"))))
(setq N (SSLENGTH B))
(setq L 0)
 (while (< L n)
   (setq eleman (ENTGET (SSNAME B L)))
   (SETQ P3 (CDR (ASSOC 10 eleman)))
   (SETQ R  (CDR (ASSOC 40 eleman)))
   (SETQ P4 (POLAR P3 (* 0.50 PI) (* 0.4 R)))
   (SETQ P5 (POLAR P3 (* 0.50 PI) (* 0.8 R)))
   (SETQ P2 (POLAR P3 (* 1.50 PI) (* 0.4 R)))
   (SETQ P1 (POLAR P3 (* 1.50 PI) (* 0.8 R)))
   (COMMAND "ARC" "C" P3 P5 P1) (setq borukapa_eleman_1 (entlast))
   (COMMAND "ARC" "C" P2 P1 P3) (setq borukapa_eleman_2 (entlast))
   (COMMAND "ARC" "C" P4 P5 P3) (setq borukapa_eleman_3 (entlast))
   (setq borukapa_tum (ssadd))
   (setq borukapa_tum (ssadd borukapa_eleman_1  borukapa_tum))
   (setq borukapa_tum (ssadd borukapa_eleman_2  borukapa_tum))
   (setq borukapa_tum (ssadd borukapa_eleman_3  borukapa_tum))
   (COMMAND "PEDIT" "M" borukapa_tum "" "Y" "J" "" "")
   (COMMAND "_HATCH" "_S" "l" "" )
  (setq L (+ L  1))
 )
(setvar "osmode"   osmode_old   )
(princ)
)
