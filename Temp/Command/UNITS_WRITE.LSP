(defun c:UNW1 ( / )
(princ (strcat "\n Cizim birimi m->1 cm->100 mm->1000..<" (rtos (BIRIM_OKU) 2 0 ) " . : " ))
(setq birim (getreal))
(if (= birim nil) (setq birim (BIRIM_OKU)))
(princ (strcat "\n Pafta olcegi.      1/<" (rtos (OLCEK_OKU) 2 0 ) ">                 : " ))
(setq olcek (getreal))
(if (= olcek nil) (setq olcek (OLCEK_OKU)))
(setq dosya (open (strcat client_path "Standard/UNIT.txt") "W"))
(princ (itoa (fix birim)) dosya)
(princ "\n" dosya)
(princ (itoa (fix olcek)) dosya)
(princ "\n" dosya)
(close dosya)
(princ)
)
