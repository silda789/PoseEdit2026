(defun c:RECHANGE (/)
(fi_)
(setq blipmode_old (getvar "blipmode"))
(setq cmdecho_old  (getvar "cmdecho" ))
(setq clayer_old   (getvar "clayer"  ))
(setq luprec_old   (getvar "luprec"  ))
(setq osmode_old   (getvar "osmode"  ))
(setvar "osmode" 0)
(command "_.Undo" "_BE")
(setq B (ssget (list (cons 0 "INSERT") (cons -4  "<OR") (cons 2 "L-POZ") (cons 2 "L-POZE") (cons -4  "OR>")  )))
(setq n (sslength b))
(setq l 0)
 (while (< l n)
        (setq en1 (ssname B l))
        (setvar "clayer"   "ren.mtr.tb" )
        (command "-insert" (strcat source_path "Standard/RL-POS") (cdr (assoc 10 (entget (ssname b l)))) (cdr (assoc 41 (entget (ssname b l)))) (cdr (assoc 41 (entget (ssname b l)))) 0 )
        (setq en2 (entlast))
        (command "rotate" en2 "" (cdr (assoc 10 (entget en1))) (/ (* 180 (cdr (assoc 50 (entget en1)))) pi ))
        (att_yaz en2 "POZ"  (a_oku en1 "PNO"))
        (if (> (strlen (a_oku en1 "ARA")) 1)
           (att_yaz en2 "TB"   (STRCAT (a_oku en1 "AD") fi (a_oku en1 "CA") "/" (a_oku en1 "ARA")))
           (att_yaz en2 "TB"   (STRCAT (a_oku en1 "AD") fi (a_oku en1 "CA")))
        )
        (setq eski_boy (RENAISSANCE_eski_boy_oku_isle (a_oku en1 "BOY")))
        (att_yaz en2 "BOY"  (strcat "L=" eski_boy))
        (if (= (cdr (assoc 2 (entget en1))) "L-POZ")
         (progn
          (if     (AND (= (atoi (a_oku en1 "IBUK")) 0) (= (atoi (a_oku en1 "SBUK")) 0))
              (progn
                  (att_yaz en2 "TIP"  "00")
                  (att_yaz en2 "A"    eski_boy)
                  (att_yaz en2 "B"    "0")
                  (att_yaz en2 "C"    "0")
              )
          )
          (if
              (or
                  (AND (> (atoi (a_oku en1 "IBUK")) 0) (= (atoi (a_oku en1 "SBUK")) 0))
                  (AND (= (atoi (a_oku en1 "IBUK")) 0) (> (atoi (a_oku en1 "SBUK")) 0))
              )
              (progn
                  (att_yaz en2 "TIP"  "11")
                  (att_yaz en2 "A"    (max (atoi (a_oku en1 "IBUK"))(atoi (a_oku en1 "SBUK"))))
                  (att_yaz en2 "B"    (- (atoi eski_boy) (+ (atoi (a_oku en1 "IBUK"))(atoi (a_oku en1 "SBUK")))))
                  (att_yaz en2 "C"    "0")
              )
          )
          (if (AND (> (atoi (a_oku en1 "IBUK")) 0) (> (atoi (a_oku en1 "SBUK")) 0))
              (progn
                  (att_yaz en2 "TIP"  "21")
                  (att_yaz en2 "A"    (max (atoi (a_oku en1 "IBUK"))(atoi (a_oku en1 "SBUK"))))
                  (att_yaz en2 "B"    (- (atoi eski_boy) (+ (atoi (a_oku en1 "IBUK"))(atoi (a_oku en1 "SBUK")))))
                  (att_yaz en2 "C"    (min (atoi (a_oku en1 "IBUK"))(atoi (a_oku en1 "SBUK"))))
              )
          )
          (att_yaz en2 "D"    "0")
          (att_yaz en2 "E"    "0")
          (att_yaz en2 "F"    "0")
          (att_yaz en2 "R"    "0")
         )
        )
        (if (= (cdr (assoc 2 (entget en1))) "L-POZE")
         (progn
          (setq eski_1YA  (atoi (a_oku en1 "1YA" )))
          (setq eski_2YA  (atoi (a_oku en1 "2YA" )))
          (setq eski_1DU  (atoi (a_oku en1 "1DU" )))
          (setq eski_2DU  (atoi (a_oku en1 "2DU" )))
          (setq eski_IBUK (atoi (a_oku en1 "IBUK")))
          (setq eski_SBUK (atoi (a_oku en1 "SBUK")))
          (att_yaz en2 "BOY" (STRCAT "L=" (itoa (+ eski_1YA eski_2YA eski_1DU eski_2DU eski_IBUK eski_SBUK))))
          (if (and (= eski_1YA eski_2YA) (= eski_1DU eski_2DU))
           (progn
            (att_yaz en2 "TIP"  "51")
            (att_yaz en2 "A"    (itoa eski_1YA  ))
            (att_yaz en2 "B"    (itoa eski_1DU  ))
            (att_yaz en2 "C"    (itoa eski_IBUK ))
            (att_yaz en2 "D"    (itoa eski_SBUK ))
            (att_yaz en2 "E"    "0")
            (att_yaz en2 "F"    "0")
            (att_yaz en2 "R"    "0")
           )
           (progn
            (att_yaz en2 "TIP"  "56")
            (att_yaz en2 "A"    (itoa (max eski_1YA eski_2YA )))
            (att_yaz en2 "B"    (itoa (max eski_1DU eski_2DU )))
            (att_yaz en2 "C"    (itoa (min eski_1YA eski_2YA )))
            (att_yaz en2 "D"    (itoa (min eski_1DU eski_2DU )))
            (att_yaz en2 "E"    (itoa eski_IBUK ))
            (att_yaz en2 "F"    (itoa eski_SBUK ))
            (att_yaz en2 "R"    "0")
           )
          )
         )
        )
          (command "erase" (ssname b l) "")
   (setq l (+ l 1))
 )
(command "_.Undo" "_E")
(setvar "blipmode" blipmode_old )
(setvar "cmdecho"  cmdecho_old  )
(setvar "clayer"   clayer_old   )
(setvar "luprec"   luprec_old   )
(setvar "osmode"   osmode_old   )
(princ)
)



(defun c:RECH (/)
(fi_)
(vl-load-com)
(setq blipmode_old (getvar "blipmode"))
(setq cmdecho_old  (getvar "cmdecho" ))
(setq clayer_old   (getvar "clayer"  ))
(setq luprec_old   (getvar "luprec"  ))
(setq osmode_old   (getvar "osmode"  ))
(setvar "osmode" 0)
(command "_.Undo" "_BE")
(setq B (ssget (list (cons 0 "INSERT") (cons -4  "<OR") (cons 2 "poz") (cons 2 "poz") (cons -4  "OR>")  )))
(setq n (sslength b))
(setq l 0)
 (while (< l n)
        (setq en1 (ssname B l))
        (setvar "clayer"   "ren.mtr.tb" )
        (command "-insert" (strcat source_path "Standard/RL-POS") (cdr (assoc 10 (entget (ssname b l)))) (/ (cdr (assoc 41 (entget (ssname b l)))) 125) (/ (cdr (assoc 41 (entget (ssname b l)))) 125) 0 )
        (setq en2 (entlast))
        (command "rotate" en2 "" (cdr (assoc 10 (entget en1))) (/ (* 180 (cdr (assoc 50 (entget en1)))) pi ))
        (att_yaz en2 "POZ"  (a_oku en1 "POZ"))
        (setq eskiaralik (RENAISSANCE_eski_boy_oku_isle (a_oku en1 "ARALIK")))
        (if (> (strlen (a_oku en1 "ARALIK")) 1)

           (att_yaz en2 "TB"   (STRCAT (a_oku en1 "ADET") fi (a_oku en1 "CAP") "/" (substr eskiaralik (+(vl-string-position (ascii "/") eskiaralik ) 2) 10)))
           (att_yaz en2 "TB"   (STRCAT (a_oku en1 "ADET") fi (a_oku en1 "CAP")))
        )
        (setq eski_boy (substr (RENAISSANCE_eski_boy_oku_isle (a_oku en1 "BOY"))3 10))
        (att_yaz en2 "BOY"  (strcat "L="eski_boy))
        (if (= (cdr (assoc 2 (entget en1))) "poz")
         (progn
          (if     (= (atoi (a_oku en1 "DEMIR_TIPI")) 1)
              (progn
                  (att_yaz en2 "TIP"  "00")
                  (att_yaz en2 "A"    eski_boy)
                  (att_yaz en2 "B"    "0")
                  (att_yaz en2 "C"    "0")
              )
          )
          (if
              (= (atoi (a_oku en1 "DEMIR_TIPI")) 2)
              (progn
                  (setq yazilar  (RENAISSANCE_eski_boy_oku_isle (a_oku en1 "BUKUM_BOYLARI")))
                  (setq yazilar2 (substr  yazilar (+(vl-string-position (ascii " ") yazilar ) 2) 20  ))
                  (att_yaz en2 "TIP"  "11")
                  (att_yaz en2 "A"    (substr yazilar 1 (vl-string-position (ascii " ") yazilar ) ))
                  (att_yaz en2 "B"    (print (substr  yazilar (+(vl-string-position (ascii " ") yazilar ) 2) 22  )))
                  (att_yaz en2 "C"    "0")
              )
          )
          (if (= (atoi (a_oku en1 "DEMIR_TIPI")) 3)
              (progn
                  (setq yazilar  (RENAISSANCE_eski_boy_oku_isle (a_oku en1 "BUKUM_BOYLARI")))
                  (setq yazilar2 (substr  yazilar (+(vl-string-position (ascii " ") yazilar ) 2) 20  ))
                  (setq yazilar3 (substr  yazilar2 (+(vl-string-position (ascii " ") yazilar2 ) 2) 20  ))
                  (att_yaz en2 "TIP"  "21")
                  (att_yaz en2 "A"    (substr yazilar 1 (vl-string-position (ascii " ") yazilar ) ))
                  (att_yaz en2 "B"    (print (substr  yazilar (+(vl-string-position (ascii " ") yazilar ) 2) (vl-string-position (ascii " ") yazilar2 )  )))
                  (att_yaz en2 "C"    (print (substr  yazilar2 (+(vl-string-position (ascii " ") yazilar2) 2) (vl-string-position (ascii " ") yazilar3 )  )))
              )
          )
          (att_yaz en2 "D"    "0")
          (att_yaz en2 "E"    "0")
          (att_yaz en2 "F"    "0")
          (att_yaz en2 "R"    "0")
          (if (= (atoi (a_oku en1 "DEMIR_TIPI")) 15)
              (progn
                  (setq yazilar  (RENAISSANCE_eski_boy_oku_isle (a_oku en1 "BUKUM_BOYLARI")))
                  (setq yazilar2 (substr  yazilar (+(vl-string-position (ascii " ") yazilar ) 2) 20  ))
                  (setq yazilar3 (substr  yazilar2 (+(vl-string-position (ascii " ") yazilar2 ) 2) 20  ))
                  (att_yaz en2 "TIP"  "51")
                  (att_yaz en2 "A"    (print (substr  yazilar (+(vl-string-position (ascii " ") yazilar ) 2) (vl-string-position (ascii " ") yazilar2 )  )))
                  (att_yaz en2 "B"    (print (substr  yazilar2 (+(vl-string-position (ascii " ") yazilar2) 2) (vl-string-position (ascii " ") yazilar3 )  )))
                  (att_yaz en2 "C"    (substr yazilar 1 (vl-string-position (ascii " ") yazilar ) ))
                  (att_yaz en2 "D"    (substr yazilar 1 (vl-string-position (ascii " ") yazilar ) ))
              )
          )
          (if (= (atoi (a_oku en1 "DEMIR_TIPI")) 13)
              (progn
                  (setq yazilar  (RENAISSANCE_eski_boy_oku_isle (a_oku en1 "BUKUM_BOYLARI")))
                  (setq yazilar2 (substr  yazilar (+(vl-string-position (ascii " ") yazilar ) 2) 20  ))
                  (setq yazilar3 (substr  yazilar2 (+(vl-string-position (ascii " ") yazilar2 ) 2) 20  ))
                  (att_yaz en2 "TIP"  "50")
                  (att_yaz en2 "A"    (substr yazilar 1 (vl-string-position (ascii " ") yazilar ) ))
                  (att_yaz en2 "B"    (print (substr  yazilar (+(vl-string-position (ascii " ") yazilar ) 2) (vl-string-position (ascii " ") yazilar2 )  )))
                  (att_yaz en2 "D"    (print (substr  yazilar2 (+(vl-string-position (ascii " ") yazilar2) 2) (vl-string-position (ascii " ") yazilar3 )  )))
              )
          )

         )
        )

          (command "erase" (ssname b l) "")
   (setq l (+ l 1))
 )
(command "_.Undo" "_E")
(setvar "blipmode" blipmode_old )
(setvar "cmdecho"  cmdecho_old  )
(setvar "clayer"   clayer_old   )
(setvar "luprec"   luprec_old   )
(setvar "osmode"   osmode_old   )
(princ)
)
