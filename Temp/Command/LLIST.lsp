(defun c:llist (/)
(setq dosya_ismi (strcat (getvar "dwgprefix") (substr (getvar "dwgname") 1 (- (strlen (getvar "dwgname")) 4 )) "-layers.txt"))
(setq dosya (open dosya_ismi "w"))
 (setq layer_bilgi (tblnext "layer" T))
  (while (/= layer_bilgi nil)
    (princ ";"  dosya)
    (princ (cdr (assoc  2 layer_bilgi)) dosya)
    (princ ";"  dosya)
    (princ (cdr (assoc 62 layer_bilgi)) dosya)
    (princ ";"  dosya)
    (princ (cdr (assoc  6 layer_bilgi)) dosya)
    (princ ";"  dosya)
    (princ "\n" dosya)
    (setq layer_bilgi (tblnext "layer" ))
  )
(close dosya)
(princ)
)
