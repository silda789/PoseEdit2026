(defun c:pozver (/)
(vl-load-com)
(command "_.Undo" "_BE")
(setq son_poz 0)
(setq poz_siralanacak_liste (list))
(princ "\n Otomatik pozlandırılacak pozları seç (Seçilen tüm pozlar otomatik pozlandırılacak)....")
(terpri)
(setq eset (ssget (list (cons 0 "INSERT") (cons 2 "RL-POS"))))
(if (= eset nil)
       (progn
         (princ "\n Daha önceden pozlandırılmış pozlar kalacak edit işlemi yapılmış pozlar pozlandırılacak. Şimdi tekrar seç... ")
         (setq eset_tum (ssget (list (cons 0 "INSERT") (cons 2 "RL-POS"))))
         (setq i 0)
         (setq eset nil)(setq eset (ssadd))
         (setq eset_once nil) (setq eset_once (ssadd))
         (while (< i (sslength eset_tum))
          (setq en (ssname eset_tum i))
              (if (= (a_oku en "TIK" ) "0")
                (ssadd (ssname eset_tum i) eset_once )
                (ssadd (ssname eset_tum i) eset      )
              )
            (setq i (1+ i))
         )
              (setq i 0)
              (while (< i (sslength eset_once))
              (setq son_poz (max son_poz (atoi (a_oku (ssname eset_once i) "POZ" ))))
              (setq i (+ i 1)))
              (setq i 0)
              (while(< i (sslength eset))
              (setq en (ssname eset i))
                     (setq j 0)
                     (while (< j (sslength eset_once))
                     (setq en_i (ssname eset_once j))
                     (if (and   (=  (cap_oku_isle (a_oku en "TB" )) (cap_oku_isle (a_oku en_i "TB" )))
                                (=  (a_oku en "TIP" ) (a_oku en_i "TIP" ))
                                (=  (a_oku en "BOY" ) (a_oku en_i "BOY" ))
                                (=  (a_oku en "A"   ) (a_oku en_i "A"   ))
                                (=  (a_oku en "B"   ) (a_oku en_i "B"   ))
                                (=  (a_oku en "C"   ) (a_oku en_i "C"   ))
                                (=  (a_oku en "D"   ) (a_oku en_i "D"   ))
                                (=  (a_oku en "E"   ) (a_oku en_i "E"   ))
                                (=  (a_oku en "F"   ) (a_oku en_i "F"   ))
                                (=  (a_oku en "R"   ) (a_oku en_i "R"   )))
                                (progn
                                    (att_yaz en "POZ"  (a_oku en_i "POZ"))
                                    (att_yaz en "TIK" "0" )
                                    (ssdel en eset)
                                    (setq i (1- i))
                                    (setq j (sslength eset_once))
                                )
                      )
                                    (if (< (sslength eset) 1) (exit))
                    (setq j (1+ j)))
              (setq i (1+ i)))
       )
)
(setq i 0)
(while(< i (sslength eset))
(setq en (ssname eset i))
(setq poz_icin_oku (list (cons  1 (cap_oku_isle    (a_oku en "TB"  )))
                         (cons  2 (a_oku en "TIP" ))
                         (cons  3 (a_oku en "BOY" ))
                         (cons  4 (a_oku en "A"   ))
                         (cons  5 (a_oku en "B"   ))
                         (cons  6 (a_oku en "C"   ))
                         (cons  7 (a_oku en "D"   ))
                         (cons  8 (a_oku en "E"   ))
                         (cons  9 (a_oku en "F"   ))
                         (cons 10 (a_oku en "R"   ))))
(if (null (member poz_icin_oku poz_siralanacak_liste)) (setq poz_siralanacak_liste (cons poz_icin_oku poz_siralanacak_liste)))
(setq i (1+ i)))
(setq poz_siralanacak_liste (vl-sort poz_siralanacak_liste (function (lambda (e1 e2)      (< (atoi (cdr (assoc 1 e1))) (atoi (cdr (assoc 1 e2))))))))
(setq poz_siralanacak_liste (vl-sort poz_siralanacak_liste (function (lambda (e1 e2) (and (= (atoi (cdr (assoc 1 e1))) (atoi (cdr (assoc 1 e2))))
                                                                                          (< (atoi (boy_oku_isle (cdr (assoc 3 e1)))) (atoi (boy_oku_isle (cdr (assoc 3 e2))))))))))
(setq i 0)
(while (< i (length poz_siralanacak_liste))
(setq poz_siralanacak_liste (subst (cons (cons 0 (+ i 1)) (nth i poz_siralanacak_liste )) (nth i poz_siralanacak_liste ) poz_siralanacak_liste))
(setq i (1+ i)))
(setq i 0)
(while(< i (sslength eset))
(setq en (ssname eset i))
(setq poz_icin_oku (list (cons  1 (cap_oku_isle    (a_oku en "TB"  )))
                         (cons  2 (a_oku en "TIP" ))
                         (cons  3 (a_oku en "BOY" ))
                         (cons  4 (a_oku en "A"   ))
                         (cons  5 (a_oku en "B"   ))
                         (cons  6 (a_oku en "C"   ))
                         (cons  7 (a_oku en "D"   ))
                         (cons  8 (a_oku en "E"   ))
                         (cons  9 (a_oku en "F"   ))
                         (cons 10 (a_oku en "R"   ))))

(setq j 0)
(while (< j (length poz_siralanacak_liste))
(if (and   (=  (cdr (assoc  1 poz_icin_oku)) (cdr (assoc  1 (nth j poz_siralanacak_liste ))))
           (=  (cdr (assoc  2 poz_icin_oku)) (cdr (assoc  2 (nth j poz_siralanacak_liste ))))
           (=  (cdr (assoc  3 poz_icin_oku)) (cdr (assoc  3 (nth j poz_siralanacak_liste ))))
           (=  (cdr (assoc  4 poz_icin_oku)) (cdr (assoc  4 (nth j poz_siralanacak_liste ))))
           (=  (cdr (assoc  5 poz_icin_oku)) (cdr (assoc  5 (nth j poz_siralanacak_liste ))))
           (=  (cdr (assoc  6 poz_icin_oku)) (cdr (assoc  6 (nth j poz_siralanacak_liste ))))
           (=  (cdr (assoc  7 poz_icin_oku)) (cdr (assoc  7 (nth j poz_siralanacak_liste ))))
           (=  (cdr (assoc  8 poz_icin_oku)) (cdr (assoc  8 (nth j poz_siralanacak_liste ))))
           (=  (cdr (assoc  9 poz_icin_oku)) (cdr (assoc  9 (nth j poz_siralanacak_liste ))))
           (=  (cdr (assoc 10 poz_icin_oku)) (cdr (assoc 10 (nth j poz_siralanacak_liste )))))
 (progn
  (att_yaz en "POZ" (itoa (+ son_poz (cdr (assoc  0 (nth j poz_siralanacak_liste ))))))
  (att_yaz en "TIK" "0" )
 )
)
(setq j (1+ j)))
(setq i (1+ i)))
(command "_.Undo" "_E")
(command "regenall")
(princ "\n Poz verme islemi tamamlandi... ")
(princ)
)
