;------------------------------------------------------------------------------;
(defun ayarlari_ekrandan_oku (/)
 (setq tik_m_key   (get_tile "tik_m_key"  ))
 (setq tik_cm_key  (get_tile "tik_cm_key"  ))
 (setq tik_mm_key  (get_tile "tik_mm_key"  ))
  (if (= tik_m_key "1") (setq cizim_birimi "1" ))
  (if (= tik_cm_key "1") (setq cizim_birimi "100" ))
  (if (= tik_mm_key "1") (setq cizim_birimi "1000"  ))
 (setq pafta_olcegi (get_tile "pafta_olcegi" ))
 (setq hazir_yazi   (get_tile "hazir_yazi"   ))
 (setq tik_rus_key  (get_tile "tik_rus_key"  ))
 (setq tik_eng_key  (get_tile "tik_eng_key"  ))
 (setq tik_r_e_key  (get_tile "tik_r_e_key"  ))
  (if (= tik_rus_key "1") (setq cizim_dili "rus" ))
  (if (= tik_eng_key "1") (setq cizim_dili "eng" ))
  (if (= tik_r_e_key "1") (setq cizim_dili "re"  ))
)
;-------------------------------------------------------------------------------
(defun hazir_yazi_liste ( / )
(setq liste nil)
(setq dosya_adi (strcat source_path "Standard/Projeisimleri.txt"))
(setq dosya (open dosya_adi "r"))
(setq yazi_liste_oku  (read-line dosya))
 (while (/= yazi_liste_oku nil)
   (setq liste (cons yazi_liste_oku liste))
   (setq yazi_liste_oku  (read-line dosya))
 )
    (close dosya)
    (setq hazir_liste (reverse liste))
)
;-------------------------------------------------------------------------------
(defun ayarlari_ekrana_yaz (/)
 (hazir_yazi_liste)
(start_list "hazir_yazi")     (mapcar 'add_list hazir_liste) (end_list)
  (if (= cizim_birimi "1000") (setq tik_mm_key "1") (setq tik_mm_key "0"))
  (if (= cizim_birimi "100") (setq tik_cm_key "1") (setq tik_cm_key "0"))
  (if (= cizim_birimi "1")  (setq tik_m_key "1") (setq tik_m_key "0"))
 (set_tile "tik_mm_key" tik_mm_key )
 (set_tile "tik_cm_key" tik_cm_key )
 (set_tile "tik_m_key" tik_m_key )
 (set_tile "pafta_olcegi" pafta_olcegi )
 (set_tile  "hazir_yazi"  hazir_yazi   )
  (if (= cizim_dili "rus") (setq tik_rus_key "1") (setq tik_rus_key "0"))
  (if (= cizim_dili "eng") (setq tik_eng_key "1") (setq tik_eng_key "0"))
  (if (= cizim_dili "re")  (setq tik_r_e_key "1") (setq tik_r_e_key "0"))
 (set_tile "tik_rus_key" tik_rus_key )
 (set_tile "tik_eng_key" tik_eng_key )
 (set_tile "tik_r_e_key" tik_r_e_key )
)
;-------------------------------------------------------------------------------
(defun ayarlari_dosyaya_yaz2 (/)
 (setq dosya (open (strcat client_path "Standard/UNIT.TXT" ) "w"))
 (princ cizim_birimi2 dosya )(princ "\n" dosya)
 (princ pafta_olcegi2 dosya )(princ "\n" dosya)
 (write-line hazir_yazi2 dosya)(princ "\n" dosya)
 (close dosya)
 (setq dosya (open (strcat client_path "Standard/TABLO_DILI.TXT" ) "w"))
 (princ cizim_dili2 dosya ) (princ "\n" dosya)
 (close dosya)
)
;-------------------------------------------------------------------------------
(defun ayarlari_dosyaya_yaz (/)
 (setq dosya (open (strcat client_path "Standard/UNIT.TXT" ) "w"))
 (princ cizim_birimi dosya )(princ "\n" dosya)
 (princ pafta_olcegi dosya )(princ "\n" dosya)
 (princ hazir_yazi dosya )(princ "\n" dosya)
 (setq hazir_yazi1 (nth (atoi (get_tile "hazir_yazi")) hazir_liste))
 (write-line hazir_yazi1 dosya)(princ "\n" dosya)
 (close dosya)
 (setq dosya (open (strcat client_path "Standard/TABLO_DILI.TXT" ) "w"))
 (princ cizim_dili dosya ) (princ "\n" dosya)
 (close dosya)
)
;-------------------------------------------------------------------------------
(defun ayarlari_dosyadan_oku (/)
 (if (= (not (open (strcat client_path "Standard/UNIT.TXT") "r")) t )
 (progn (setq dosya (open (strcat client_path "Standard/UNIT.TXT") "w"))
 (princ "1" dosya )(princ "\n" dosya)
 (princ "1" dosya )(princ "\n" dosya)
 (princ "1" dosya )(princ "\n" dosya)
 (princ "1" dosya )(princ "\n" dosya)
 (close dosya)))
 (setq dosya (open (strcat client_path "Standard/UNIT.TXT") "r"))
  (setq cizim_birimi (read-line dosya) )
  (if (= cizim_birimi nil ) (progn (setq cizim_birimi "1000")) (setq cizim_birimi cizim_birimi ))
  (setq pafta_olcegi (read-line dosya) )
  (if (= pafta_olcegi nil ) (progn (setq pafta_olcegi "100")) (setq pafta_olcegi pafta_olcegi ))
  (setq hazir_yazi   (read-line dosya) )
  (if (= hazir_yazi nil ) (progn (setq hazir_yazi "0")) (setq hazir_yazi hazir_yazi ))
 (close dosya)
 (setq dosya (open (strcat client_path "Standard/TABLO_DILI.TXT" ) "r"))
  (setq cizim_dili (read-line dosya) )
  (if (= cizim_dili nil ) (progn (setq cizim_dili "1")) (setq cizim_dili cizim_dili ))
 (close dosya)
)
;-------------------------------------------------------------------------------
(defun ayarlari_dosyadan_oku2 (/)
 (setq dosya (open (strcat client_path "Standard/UNIT.TXT") "r"))
  (setq cizim_birimi2 (read-line dosya) )
  (setq pafta_olcegi2 (read-line dosya) )
  (setq hazir_yazi2   (read-line dosya) )
 (close dosya)
 (setq dosya (open (strcat client_path "Standard/TABLO_DILI.TXT" ) "r"))
  (setq cizim_dili2 (read-line dosya) )
 (close dosya)
)
;-------------------------------------------------------------------------------
(defun cizim_birimi_act ( / )
 (ayarlari_ekrandan_oku)
 (ayarlari_dosyaya_yaz)
)
;-------------------------------------------------------------------------------
(defun pafta_olcegi_act ( / )
 (ayarlari_ekrandan_oku)
 (ayarlari_dosyaya_yaz)
)
;-------------------------------------------------------------------------------
(defun tablo_dili_act ( / )
 (ayarlari_ekrandan_oku)
 (ayarlari_dosyaya_yaz)
)
;-------------------------------------------------------------------------------
(defun hazir_yazi_act        ( / )
;(write-line (nth (atoi (get_tile "hazir_yazi")) hazir_liste) dsy) (close dsy)
(ayarlari_dosyaya_yaz)
)
;-------------------------------------------------------------------------------
(defun ayarlari_dosyaya_yaz2_act  ( / )
 ;(ayarlari_dosyadan_oku2)
 (ayarlari_dosyaya_yaz2)
 (done_dialog 5) ; Dialog state
)
;-------------------------------------------------------------------------------
(defun ayarla_act  ( / )
 (ayarlari_ekrandan_oku)
 (ayarlari_dosyaya_yaz)
 (done_dialog 4) ; Dialog state
)
;-------------------------------------------------------------------------------
; If dialog state equal 4 write this place....
(defun ayarla_action ( / )
(princ)
)
;-------------------------------------------------------------------------------
tik_rus_key
tik_eng_key
tik_r_e_key
(defun c:Unw ( / )
(setvar "cmdecho" 0)
(setq Dialog_id (load_dialog (strcat source_path "Command/Unw.dcl")))
(if (not (new_dialog "Standart_Ayarlar_dialog" Dialog_id)) (exit))
 (action_tile "cizim_birimi"    "(cizim_birimi_act)"   )
 (action_tile "pafta_olcegi"    "(pafta_olcegi_act)"   )
 (action_tile "hazir_yazi"      "(hazir_yazi_act)"     )
 (action_tile "M_T_Y"          "(M_T_Y_act)"         )
 (action_tile "ayarla"          "(ayarla_act)"         )
 (action_tile "ad_cik"          "(ayarlari_dosyaya_yaz2_act) (done_dialog)" )
 (action_tile "cancel"          "(ayarlari_dosyaya_yaz2_act) (done_dialog)" )
(ayarlari_dosyadan_oku)
(ayarlari_dosyadan_oku2)
(ayarlari_ekrana_yaz)
(setq dialog-state (start_dialog))
 (if (= dialog-state 4) (ayarla_action))
(unload_dialog Dialog_id)
(setvar "cmdecho" 1)
(princ)
)
;------------------------------------------------------------------------------;
